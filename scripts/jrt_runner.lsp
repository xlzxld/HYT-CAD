;;; ============================================================================
;;; 程序名 : 加热条自动绘制工具 (jrt_runner.lsp)  v9.36
;;; v9.37 : 真 2007 专修(坑 #74 终局): c:JRT 原流程"模板框→参数框"两连开,
;;;          模板框关闭瞬间在用户精简版 2007 上触发菜单 Automation 错误风暴
;;;          打断命令(仅通用二必现; 直连 (dt:jrt2-process) 两次全部出图正常,
;;;          几何本体无任何问题)。修复: 模板单选合并进参数对话框(单开一个
;;;          DCL, 非当前模板的参数置灰), c:JRT 不再打开模板选择框 ——
;;;          对话框链路只剩参数框一次开关(该形态已在用户机实测安全)。
;;;          模板记忆不变(mem [模板] template=下标, 下次打开自动选中)。
;;;          dt:jrt-template-dialog / dt:jrt-template-dcl-lines 删除。
;;;
;;; v9.36  : 通用二封闭线改「本体在 JRT + JRTFBX 定位副本」(用户定案):
;;;          v9.34 曾把通用二破口封闭线整体挪到 "JRTFBX", 破坏"JRT = 完整
;;;          加热条"契约 —— 外协加工按图层白名单取线, 漏掉 JRTFBX 就致出图
;;;          缺封闭线(且需长期维护"JRT+JRTFBX 并集"隐性契约)。改为: 本体
;;;          回归 "JRT"(加热条与 v9.33 完全一致), 另在 "JRTFBX" 描一份
;;;          同几何定位副本(dt:jrt2-trace), 供另一项目建模脚本按层定位;
;;;          JRTFBX 不在外协白名单 → 定位层不混进数据图纸/精雕出图。
;;;          重跑幂等清理仍含 JRTFBX; 产物检查口径回归单层 "JRT"。
;;; v9.35  : 通用一封闭线回退(需求澄清: 加热条封闭线只加在"出线口", 且仅
;;;          通用二可实现 —— 通用一是"半成品"嵌套轮廓, 根本没有出线口,
;;;          其直线帽封闭线属端帽, 与"出线口封闭线"不是一回事): 撤销
;;;          v9.34 对通用一的全部改动 —— dt:jrt-cap-line 帽线回归 "JRT";
;;;          dt:jrt-snapshot/dt:jrt-diff 与 dt:jrt-build 快照回归单层;
;;;          通用一建层/重跑清理/完成提示语一并回退。保留: 通用二破口封
;;;          闭线 "JRTFBX" + 全图层配色重排。(注: 该"通用二封闭线在
;;;          JRTFBX"已被 v9.36 取代 —— 见上)
;;; v9.34  : 加热条封闭线独立图层 "JRTFBX"(用户需求): ①通用二破口封闭线
;;;          改放 "JRTFBX"(浅橙 21); ②[已回退, 见 v9.35] 通用一直线帽的
;;;          帽线(含 capr≈0 直角帽线与 capr>=半宽 的整弧替换帽)同款改动,
;;;          以及 dt:jrt-snapshot/dt:jrt-diff 并集 —— 误判为通用一也适用;
;;;          ③重跑幂等: 通用二句柄清理 member 扩 "JRTFBX"(通用一清理扩
;;;          JRTFBX 已于 v9.35 回退); ④回归 check_jrt2_out.py 口径改两层
;;;          并集(几何不变, 断言数值不变)。同批: dt:ensure-layer 已存在图
;;;          层也校正为登记色(全图层配色重排, 配合 flb v10.11)。
;;; v9.33  : 加载横幅精简为一行(命令教学移出加载期, 用户从菜单点击使用)
;;;          + 新增 *dt-jrt-ver* 版本单一来源 —— 横幅引用变量, 发版只改
;;;          头注与常量两处相邻位置(根治横幅版本号长期滞后, 本次 v9.29
;;;          → v9.33 追平)。
;;; v9.32  : 体检B-03/B-04 死代码清理(行为零变化): ①删除重复定义的
;;;          dt:jrt-undo-end(连续两个逐字相同定义, v9.17~9.21 括号修补
;;;          残留); ②删除全库零调用的 dt:jrt2-out-end(v9.27 实际落地为
;;;          hook-one 内联里外分类, 函数从未被调用; 同步移出
;;;          check_lisp.py 关键函数名单, 历史定义见 git)。
;;; v9.31  : 体检A-01/B-08: ①通用二重跑幂等 —— 重跑清理只删图层 "JRT"
;;;          的句柄, 而出线口产物(颈线两壁/封口/圆角, dt:jrt2-neck)全在
;;;          "JT" 层且函数无存在性守卫 → 连跑两次逐项叠加永不清除; 清理
;;;          改 member '("JRT" "JT")(仅清 *jrt2-made* 记忆句柄, flb 假体
;;;          的 JT 实体不在记忆中, 不受影响)。②dt:jrt2-wall-tan 终点侧
;;;          取样补 v9.25 双判规范(交点距壁端 <0.01 时 getpointatdist
;;;          越界返 nil, (nth 0 p2) 抛参数类型错误)。
;;; v9.30  : 体检A-02根治(与 cx v11.4 / flb v10.7 同期): LWPolyline 的
;;;          ObjectName 实为 "AcDbPolyline", dt:poly-pts/dt:seg-rebuild
;;;          的 is-2d 单名 "(= ... \"AcDbLWPolyline\")" 判定恒 nil →
;;;          多段线经 cut/trim 重建时 2D 平铺坐标按 3 元素切分(顶点全
;;;          错位)且误建 3D 多段线。两处改双名 member; dt:set-endpoint
;;;          同款死子句清除。新增回归 tools/check_audit_fixes.py。
;;; v9.29  : 通用二通道线外端复原纠正: v9.26 起"外端延长保留"理解反了 ——
;;;          用户确认 出线端加热条不得高于 JRTDW 定位线。hook_ext 延长仅
;;;          求交用, 求交后外端一律裁回定位线原始端点(垂足投影
;;;          vlax-curve-getClosestPointTo, 与区域分类解耦)。其余不动。
;;; v9.28  : 通用二出线口过渡弧根治: 旧版把外壁曲线在角点处当"切直线"做
;;;          线-线圆角(t=r·cot(α/2)), 壁为弧时切点落在切线上而非弧上
;;;          (1714 实测: 圆角心距外壁圆心 41.52≠29+12=41, 肩部缺口 0.65mm
;;;          → 内偏 4/8 放大为 1.33/1.78mm → 环链断(传播阈 0.5) → 破口封
;;;          口"外端↔最内端"误配出 4 条 X 斜线+肩部错台, 用户判一塌糊涂)。
;;;          现按角点密切圆(一阶/二阶导求 Rw/Cw)解析求真切圆角: 圆角心
;;;          =p+t·d+r·m, 解 |c-Cw|=Rw+r(外切)/Rw-r(内切)一元二次, 壁剪在
;;;          真切点 tp、通道裁在 fp=p+t·d, 三段端点严格重合且 G1 相切
;;;          (新增 dt:jrt2-osculating / dt:jrt2-true-fillet, hook-arc 增
;;;          wall 参); 直壁(曲率≈0)/求解失败回退线-线公式, 行为不劣于旧版。
;;;          封口/内偏/颈线规则不动。新增回归: tools/check_jrt2_out.py
;;;          (断言口径出自 1714 测试图+默认参数; 该测试图 2026-09-09 移出
;;;          仓库, 重跑回归需自备同图出产物)。
;;; v9.27  : 用户六图手工流程定稿(图2→图3 的裁剪/复原步):
;;;          ①硬 bug: v9.22 的 pw=stub×wall 求交写在 (vla-delete wall) 之后,
;;;            对已删实体求交恒失败 → e-out 退化成"起笔端", 通道线保留侧
;;;            随画向翻转(留里删外)—— 移到删除之前计算, 兜底路径自此可用;
;;;          ②里外判定几何化: 定位线两端按轮廓围合区域(dt:jrt2-region-
;;;            edges-n+pt-inside)分里外 —— 长定位线一头埋板内时, 不再用
;;;            "离外壁交点远=板边"错误假设; 过渡弧方向 d=里端→外端,
;;;            切点/弧向/开口全部朝板边(图4); 通道线裁剪保留[切点→板边端]
;;;            (板内伸出段连同内端延长删除, 外端延长复原保留, 图3), 新助手
;;;            dt:jrt2-out-end/dt:jrt2-seg-rebuild; 两端同里/同外(贴壁短线
;;;            旧画法) → 自动回退 v9.22 启发式, 行为不变;
;;;          ③封口规则不动(用户定案): 圆弧连接正确后, 封线只出现在出线端。
;;; v9.26  : 用户三轮实测修复:
;;;          ①新增参数 jrt2_hook_ext(出线口通道延伸, 默认 5.0, 进参数框/
;;;            ini/记忆; 填 0 = 恢复旧行为): 外壁为圆弧/圆时, 壁面在
;;;            ±half_w 偏移处"让开", 通道线短线段够不着外壁 → 整个开口
;;;            被跳过(实测日志"通道线未与外壁相交")。现 ch1/ch2 生成后
;;;            双端各延 ext 再走找壁/过渡弧/裁剪全链路(延伸后的线即持久
;;;            产物, 外端压进颈线走廊);
;;;          ②颈线反向二次根治: 包围盒中心判据只对凸形 FLB 可靠, L 形/
;;;            带台阶外框的凹区会翻错方向(用户实测"某些情况仍入侵 FLB")。
;;;            主判据改为 FLB 围合区域奇偶点内判定(新增 dt:jrt2-region-
;;;            edges-n, 颈线按 24 段/曲线采样——R≤400 弧弦割误差 <5mm 探
;;;            针, 12 段版会吞弧中段致漏判), 判据不可得时才回退包围盒
;;;            中心, 再回退保持原向。
;;; v9.25  : 用户实测修复(崩溃 + 方向判据换用户方案):
;;;          ①根治 "参数类型错误: numberp: nil"(v9.24 引入): vlax-curve 的
;;;            getpointatparam/getdistatparam 越界会返回 nil 而不抛错
;;;            (实证范本 wx_runner 采样函数双判写法), v9.24 新助手只判
;;;            error-p → nil 点混入边集 → (min (cadr a) nil) 崩; 全线补
;;;            (error-p)+非nil 双判(curve-edges/curve-len/mid-pt/pt-inside);
;;;          ②内偏主判据改用户定案规则: 锚段两候选各整环传播成 RingA/RingB
;;;            (新 dt:jrt2-propagate 非破坏式), 分别求"环到 FLB 壁的平均
;;;            最近距离"(dt:jrt2-flb-score), 距 FLB 更近者=方向反了 → 取
;;;            更远环 —— JRT 恒朝内不再依赖任何线画法; 围合区域奇偶判定
;;;            降为回退 1, JRTDW 就近回退 2;
;;;          ③判定阶段零删除、胜者定后一次性清理落选候选; 候选创建即登记
;;;            句柄进 *jrt2-made* —— 任何中途出错, 下次运行先自动清走废线;
;;;          ④"内向偏移次数失效"实为 ① 的伴生现象(崩溃在删除落选候选之前,
;;;            ±两圈同时留在 JRT 层); 已修, 重测前请先手动删掉崩溃残留环。
;;; v9.24  : 方向随机根治(用户定案: JRTDW 手绘习惯不该决定内外):
;;;          ①嵌套内偏不再"朝 JRTDW 选边", 改几何判定 —— "内" = 该条
;;;            轮廓围合区域的内部(轮廓采样成边集+自由端贪心配对封口,
;;;            +X 射线奇偶规则判点在内); 锚段=条内最长段, 候选取中点在
;;;            区域内的唯一一侧; 链传播不变; 歧义(0/多候选在内)或区域
;;;            不可判定时才回退旧"离 JRTDW 近"规则;
;;;          ②出线口颈线(JT 层, FLBJT)方向根治: 颈线从交点沿 JRTDW 走出
;;;            5mm 若仍落在 FLB 围合区域内 → 反向 —— 颈线恒朝 FLB 外侧,
;;;            不再入侵 FLB, 与 JRTDW 画向无关;
;;;          ③JRTDW 职责缩减为: 出线口位置标记(及①歧义兜底), 不再参与
;;;            内外方向判断。
;;; v9.23  : 修复 "no function definition: PW" —— v9.22 误用 let 特殊形式
;;;          (AutoLISP 无 let), 解释器把绑定变量 pw 当函数调用。改为普通
;;;          setq + 局部表 pw。
;;; v9.22  : 修复通用二出线口通道线方向随机(用户实测截图): 通道线保留段
;;; v9.21  : 根治"no function definition: DT:JRT2-HOOK-ONE"(坑 #73):
;;;          v9.17 引入的 dt:jrt-undo-mark 函数体少 1 个右括号, 其 defun
;;;          吞掉了后续多个函数的 defun(含 ch-exist 区段与 hook-one —— 两处
;;;          缺口叠加, 文件总平衡却为 0, 字符串匹配型检查全部漏检)。被吞
;;;          函数加载时只是内层表达式, 永不定为全局函数, 运行期必报
;;;          no function definition。修复: undo-mark 补闭合 + ch-exist 尾
;;;          补闭合(程序化计算, 非手数); 新增 tools\check_defun_depth.py
;;;          门禁(defun 行首深度必须为 0)防再犯。
;;; v9.17  : 修复 v9.16 运行报「调用(*push-error-using-command*)前无法从
;;;          *error* 调用(command)」(坑 #69 在本文件的残留): ①根因 = 出线口
;;;          交点解析误用 cadr 取 dt:cross-points 的返回对 (obj . pts) ——
;;;          cadr 拿到的是首个交点(裸点), foreach 对其坐标数字求 distance
;;;          抛类型错误, 异常传入 *error* 后其 (dt:jrt-undo-end) 非法
;;;          调用掩盖了真错。改为 cdr 取交点列表 + cross-points 加 catch;
;;;          ②本文件全部 (command "_.UNDO" "BE"/"E") 改 COM 撤销标记
;;;          (dt:jrt-undo-mark/-end, 同 wx v2.2 坑 #69 定案), *error* 不再
;;;          碰 (command); 用户建议的 command-s 会破坏 2007~2011 兼容故未采。
;;; v9.16  : 通用二「单线自动补边」按用户截图定稿重写(v9.15 把出线口误判为
;;;          "端部喇叭", 生成几何不符, 已废弃): 用户只画 ①外壁整圈(JRT 层;
;;;          请用直线/圆弧/开放多段线, 勿用闭合多段线) ②JRTDW 定位短线
;;;          (每处出线口一条, 贴着外壁指向板边)。脚本自动完成旧手工三步:
;;;            偏移 = JRTDW 朝两边偏 jrt2_half_w → 出线通道两壁线(JRT 层);
;;;            裁剪 = 外壁在通道处开口(切口到过渡弧切点为止);
;;;            圆角 = 外壁断头↔通道线过渡弧 jrt2_end_r(钝/锐角按 r/tan(α/2)
;;;                   解析, 直角即 R12)。
;;;          生成件(通道线/过渡弧/切口后壁段)为持久源线, 不入重跑清理表,
;;;          与手画产物同权; 重跑幂等(已开处自动跳过); 之后走原嵌套引擎。
;;; v9.15  : (已被 v9.16 取代) 首版单线补边——把出线口误判为"端部喇叭",
;;;          生成几何与用户需求不符, 未交付使用。
;;; v9.14  : 健壮性修复(与 offset v10.6 / slot v10.3 / dt_start v2.8 同期,
;;;          几何行为零变化):
;;;          1) LD 源图层混入文字/块等非曲线实体时不再崩溃 —— c:JRT 取
;;;             LD 后统一按 dt:curve-p 过滤(原 dt:jrt-touch-p/jrt-free-ends
;;;             对全量对象直接求端点, 无 catch 无过滤, 会抛"参数类型错误"
;;;             中断); jrt-trim/jrt-fillet 的 LD 引用同步过滤;
;;;          2) cut-params 多段线分支 getparamatpoint 返回 nil 时剔除再
;;;             排序(nil 进 vl-sort 报 bad argument type);
;;;          3) 对话框 load_dialog/start_dialog 包 catch 且保证
;;;             unload_dialog 执行; ini/dcl 文件句柄异常兜底关闭;
;;;          4) c:JRT 的 *error* 兜底闭合 UNDO 组;
;;;          5) 参数应用增加负值校验(负值回退当前值);
;;;          6) cross-points 加包围盒预过滤(补 dt:rect-bbox 双绑定兼容
;;;             库副本, bbox 不相交跳过 COM 求交, 结果不变, 大图提速)。
;;; v9.13  : 全面审查定稿版(与 offset v10.5 / slot v10.1 / dt_start v2.7
;;;          同期): 1) 参数框数值读取 atof→distof(垃圾输入不再被静默当成 0,
;;;          坑 #54); 2) INI 节名解析改用"截到行尾再裁方括号", 修复 AutoCAD
;;;          2021 之前中文节名(如"[通用一]")残留 "]" 导致配置节永远匹配不上
;;;          的问题; 3) 记忆文件不再重复写出第二个 [模板] 节; 4) 补声明全部
;;;          遗漏的 foreach/setq 局部变量(dt:jrt-decide 的 o、dt:jrt2-neck 的
;;;          p/sgn/wx 等此前泄漏为全局); 5) 闭合多段线判定补
;;;          vl-catch-all-error-p; 6) 移除出线口相交处的遗留【调试】输出。
;;; v9.12  : 参数默认值外置 jrt_runner.ini(按模板分节, 记事本可改, 弹框即生效);
;;;          参数记忆 jrt_runner_mem.ini(按模板各一套, 确定参数框自动保存,
;;;          上次模板+上次值跨会话恢复); 恢复默认 = ini 配置的默认值。
;;; v9.11b : dt:jrt-find-dcl 弃用旧 findfile 候选链(v95~v98 文件名已不存在),
;;;          统一为 *dt-script-dir* 确定性模式(与 offset/slot 一致,
;;;          由 dt_start v2.1 引导器注入目录)。
;;; 适用   : AutoCAD 2024 (AutoCAD 2007 及以上版本均可)
;;; 多模板 : v9.8 起支持多套规则模板(dt:jrt-template-table 内置注册)。
;;;          JRT 执行时先弹独立模板选择框(单选列表), 确定后采用该模板
;;;          的参数默认值并按其规则生成; 主流程(偏移/裁剪/多层递进)共用,
;;;          模板通过"环节覆盖表"替换个别环节, 可覆盖 5 个环节:
;;;            decide     端帽判定  (默认 dt:jrt-decide, 签名 (ld-vlas matched))
;;;            cap-circle 圆帽几何  (默认 dt:jrt-cap-circle, 签名 (plan ents hw))
;;;            cap-line   直线帽几何(默认 dt:jrt-cap-line, 签名 (plan ents hw inset capr))
;;;            build      单层全流程(默认 dt:jrt-build, 签名 (hw inset r capr plans))
;;;            process    主流程整体(v9.9 新增, 无默认函数; 签名无参, 覆盖后
;;;                       整个流程由该函数自管, 不再走内置 LD/RZ 流程)
;;;          新增模板 = 在 dt:jrt-template-table 加一行(名称/说明/参数默认表/
;;;          覆盖表), 需要不同环节时新增覆盖函数 defun 并在覆盖表登记,
;;;          交付新版本文件; 覆盖函数签名须与默认函数完全一致(process 无默认
;;;          函数)。参数默认表只列该模板用到的参数键, 参数框按模板动态显示。
;;; 功能   : "LD"图层中心线向两侧各偏移 流道线偏移距离(默认29) → "JRT"图层
;;;          (黄色), 生成多层完整嵌套的加热条半成品轮廓(外层+内向偏移
;;;          jrt-inner-count 次(默认2), 每次向内收 jrt-inner-step(默认4)):
;;;          1) 区域裁剪: 侵入其他流道带状区域(±半宽)的段删除, 交叉处断开;
;;;          2) 断口圆角: 断口两线圆弧连接(R=圆角半径, 不足相切自动递减;
;;;             内层圆角逐层 +步长 递增, 默认 19→23→27, 与端帽圆 29/25/21
;;;             同为同心嵌套弧: 交汇肩部圆心=(半宽+R)处, 内层半宽收 step、
;;;             圆角加 step, 圆心不动);
;;;          3) 通道端帽(每层同款):
;;;             端帽形式按"相邻通道条带内壁间距"判定(全端头统一在第一层
;;;             判定一次, 各层共用同一形式):
;;;             - 间距≈偏移值(29) 且端头匹配到 RZ 热咀圆 → 圆帽: 在 RZ 圆心
;;;               处画整圆 R=半宽(与两条偏移线相切), 侧线端头修到切点;
;;;             - 间距超过偏移值 / 无相邻通道 / 无 RZ → 直线帽(v9.6 重构):
;;;               按"原封闭线平面=LD 端点平面(test.dxf 实测)"向通道内偏移
;;;               封闭线内偏移距离(默认11) 确定封闭线位置, 封闭线与两条相接
;;;               偏移线圆弧衔接 —— 封闭线圆角半径R(默认29) >= 半宽 时直接
;;;               替换为一个与两测线相切的圆弧(圆心=帽线中点向内偏半宽,
;;;               默认参数下 40-11=29 恰为 RZ 圆心, 与圆帽外轮廓一致);
;;;               < 半宽 时画直线封闭线+两端解析法圆角, 侧线端头修到切点,
;;;               裁掉端点平面方向多余的线段。
;;;          "通用二"模板(v9.9, v9.10 扩展出线口, v9.24/25 方向判定几何化):
;;;          源线="JRT"图层手画曲线(非 LD), 参数= 向内偏移步长/内向偏移
;;;          次数/出线颈线长度/出线颈线偏移/出线封口圆角R/出线相交圆角R;
;;;          第 k 层把每段源线向"内侧"内偏 k×步长(v9.25 判据链: 锚段两
;;;          候选各整环传播, 取离 FLB 壁更远的一环=朝内(用户定案); FLB
;;;          不可测→围合区域射线法→JRTDW 就近兜底; 与 JRTDW 画向无关);
;;;          不裁剪/不倒角/不端帽 ——
;;;          出线的每个"头"用一条直线把最外侧与最内侧端头连起来(两头各
;;;          一条)成闭环; 源线保留, 上一轮产物按句柄记忆在重跑时先删。
;;;          出线口(v9.10): JRTDW 与 "FLB" 相交, 从交点朝 FLB 外侧(v9.24,
;;;          恒不入侵 FLB)画构图颈线 → ±35 偏移成两壁(构图颈线随即删除) →
;;;          远端封闭线封口+两角 R15 圆角 → 两壁与原 JT 线相交处裁掉走廊内
;;;          多余 JT 线段, 相交处 R15 圆角(弧向与 JRT 出线处一致); 逻辑复用
;;;          分流板裁剪链; 单条 JT 线裁剪失败仅跳过并告警不中断。
;;; 版本   : v9.5 = 首版(三层嵌套轮廓/交汇裁剪+圆角/端帽按相邻通道内壁
;;;          间距判定 RZ 整圆帽/直线帽, 命令 JRT/JRTPARAM)。
;;;          v9.6 = 直线帽重构: 封闭线与两条相接偏移线圆弧衔接(半径
;;;          >=半宽时整弧替换); 参数改名 流道线偏移距离/封闭线内偏移距离;
;;;          新增 封闭线圆角半径R / 内向偏移次数(层数参数化)。
;;;          v9.7 = 圆角半径默认 29→19; 内层圆角改为逐层 +步长 递增
;;;          (19→23→27, 同心嵌套弧; 原为递减 19→15→11, 方向错误)。
;;;          v9.8 = 多模板框架: 模板注册表 + 独立选择框 + 环节覆盖分发
;;;          (dt:jrt-stage); 现有逻辑登记为内置"通用"模板。
;;;          v9.9 = 新增"两点式"模板(JRT 源线朝 JRTDW 定位线内偏嵌套 +
;;;          出线两头各一线连最内最外成闭环); 参数框按模板动态显示参数
;;;          项; 环节覆盖新增 process(主流程整体); 产物按句柄记忆重跑先删。
;;;          v9.10 = 模板更名: 通用→通用一、两点式→通用二; 通用二新增
;;;          出线口(JRTDW×FLB 颈线/双壁/远端封口圆角/裁走廊内 JT 线/
;;;          相交圆角, 新增 4 参数: 颈线长度65/颈线偏移35/封口R15/相交R15);
;;;          通用二消息前缀【两点式】→【通用二】。
;;;          v9.11 = 出线口修正: 壁裁剪侧改为保留 cap 侧/裁 pint 侧;
;;;          相交圆角改专用 dt:jrt2-junction —— 壁切点沿朝 cap 方向、
;;;          JT 保留段沿远离走廊方向, 弧倒掉走廊口尖角, 与
;;;          JRT 出线处圆弧同向(v9.10 弧向做反); 修 snapshot ename 误用
;;;          handent 的 stringp 崩溃。
;;; 来源   : 仿 cx_runner 先例的独立脚本(助手函数自 flb_runner v9.5
;;;          逐字复制, 专属逻辑全部 dt:jrt-* 前缀), 可与主脚本/出线槽脚本
;;;          同时加载互不影响(参数表/对话框/dcl/回调均已改名隔离;
;;;          fillet-pair/cut-curve 因 slot 版签名不同也改名隔离)。
;;; 前提   : 先运行 FLB(flb_runner)使 "RZ" 图层存在; 运行本脚本时
;;;          "FBX" 封闭线图层已被 OFF 收尾并层移除 —— 本脚本不读 FBX,
;;;          端帽平面直接取 LD 端点平面推导。
;;; 图层   : "JRT" = 加热条(黄色 2, 产物同层; 通用一模板=纯产物层重跑全清;
;;;          通用二模板=源线层不清理, 上一轮产物按句柄记忆重跑先删)。
;;;          "JRTFBX" = 加热条封闭线定位层(浅橙 21, v9.36: 通用二破口封闭
;;;          线的同几何定位副本 —— 本体在 "JRT"; 供另一项目建模脚本按层
;;;          定位。不在外协加工白名单, 不进数据图纸/精雕出图; OFF 预建
;;;          15 层含本层, 重跑随产物一并清理)。
;;;          "JRTDW" = 加热条定位图层(通用二: 标记每处出线口位置, 一条
;;;          线穿过外壁指向板边; v9.24 起内外方向由几何判定, 与其画向无
;;;          关, 仅在轮廓围合区域不可判定时作兜底基准)。
;;;          "JT" = 分流板假体(OFF 产物); 通用二出线口会把颈线/两壁/
;;;          封口线画上 JT, 并裁掉走廊带内的原 JT 线段。
;;; 加载   : APPLOAD 选择本文件加载(jrt_runner.dcl 由脚本自动生成)。
;;; 命令   : JRT      —— 弹出参数框, 确定后执行加热条全流程(取消中止)
;;;          JRTPARAM —— 只弹出参数框改参数, 不执行
;;; 已知限制: 与主脚本一致(多段线重建丢凸度/闭合多段线跳过等);
;;;          端头落在其他通道带状区域内时该端侧壁可能已被裁掉, 跳过端帽
;;;          并告警; RZ 圆心不在任何 LD 轴线上(垂距>0.5)时该圆不参与匹配。
;;; 说明   : 本文件必须 UTF-8 with BOM 编码(中文注释); 自动生成的
;;;          jrt_runner.dcl 为 ANSI/GBK(系统代码页)。
;;; ============================================================================

(vl-load-com)  ; 加载 Visual LISP 扩展, 使 vla-* 系列函数可用

;; 版本单一来源: 发版时与头注同行更新; 加载横幅引用本值(防两处手抄脱节)
(setq *dt-jrt-ver* "v9.37")

;; 坑 #69(v9.17): 撤销组统一走 COM 标记 —— *error* 与普通代码都不再碰
;; (command); 无开放标记时 EndUndoMark 无副作用, 双重 catch 兜底
(defun dt:jrt-undo-mark ( )
  (vl-catch-all-apply
    '(lambda ( )
       (vla-StartUndoMark (vla-get-activedocument (vlax-get-acad-object))))))

(defun dt:jrt-undo-end ( )
  (vl-catch-all-apply
    '(lambda ( )
       (vla-EndUndoMark (vla-get-activedocument (vlax-get-acad-object))))))

;; ============================================================================
;; 加热条参数 —— 由 dt:jrt-param-table 驱动(默认值/预填/应用/恢复默认),
;; 与 flb_runner / cx_runner 的参数表相互独立, 同时加载互不影响。
;; ============================================================================
(setq dt:jrt-param-table
      (list
        (list "jrt_offset"      '*jrt-offset*      29.0) ; 流道线偏移距离(半宽, 通用一)
        (list "jrt_cap_inset"   '*jrt-cap-inset*   11.0) ; 封闭线内偏移距离(通用一)
        (list "jrt_fillet_r"    '*jrt-fillet-r*    19.0) ; 圆角半径(交汇断口, 通用一)
        (list "jrt_cap_r"       '*jrt-cap-r*       29.0) ; 封闭线圆角半径R(通用一)
        (list "jrt_inner_step"  '*jrt-inner-step*  4.0)  ; 向内偏移步长(通用一/二)
        (list "jrt_inner_count" '*jrt-inner-count* 2.0)  ; 内向偏移次数(通用一/二)
        (list "jrt2_neck_len"   '*jrt2-neck-len*   65.0) ; 出线颈线长度(通用二)
        (list "jrt2_neck_off"   '*jrt2-neck-off*   35.0) ; 出线颈线偏移(通用二)
        (list "jrt2_close_r"    '*jrt2-close-r*    15.0) ; 出线封口圆角R(通用二)
        (list "jrt2_trim_r"     '*jrt2-trim-r*     15.0) ; 出线相交圆角R(通用二)
        (list "jrt2_half_w"     '*jrt2-half-w*     16.5) ; 单线补边: 壁线距定位线半宽(通用二)
        (list "jrt2_end_r"      '*jrt2-end-r*      12.0) ; 单线补边: 端部喇叭R(通用二)
        (list "jrt2_hook_ext"   '*jrt2-hook-ext*    5.0))) ; 出线口通道延伸: 通道线双端加长量, 0=旧行为(通用二)
(foreach p dt:jrt-param-table (set (cadr p) (caddr p)))

;; ============================================================================
;; 参数配置与记忆(v9.12): 默认值外置 jrt_runner.ini(按模板分节, 记事本可改,
;; 每次弹框前重读=随时生效); 上次值记忆 jrt_runner_mem.ini(按模板各一套,
;; 确定参数框时自动保存, 上次模板+上次值跨会话恢复)。
;; 解析只认"键 = 数值"行, 注释/空行/未知键跳过; 全程 vl-catch-all 保护,
;; 文件缺失/损坏静默回退代码内置默认。命名带 dt:jrt- 前缀防同加载覆盖(坑 #46)。
;; 函数在此定义, 启动 (dt:jrt-cfg-boot) 在文件尾调用(定义须先于执行)。
;; ============================================================================
(setq *jrt-cfg* nil   ; 配置(默认值) ((节 (键 . 值)...) ...) 节=模板名
      *jrt-mem* nil)  ; 记忆(上次值)   同结构 + [模板] template=下标

;; 配置/记忆文件目录: 优先 dt_start 注入的脚本目录, 无则 TEMP(与 find-dcl 同规则)
(defun dt:jrt-cfg-dir ( / )
  (if (and *dt-script-dir* (/= *dt-script-dir* ""))
    *dt-script-dir*
    (getenv "TEMP")))

;; 单行 "键 = 数值" → (键 . 值); 无等号/空值/非数值返回 nil(distof 校验, 0 合法)
(defun dt:jrt-cfg-kv (ln / p k vs n)
  (setq p (vl-string-search "=" ln))
  (if p
    (progn
      (setq k (vl-string-trim " \t" (substr ln 1 p))
            vs (vl-string-trim " \t" (substr ln (+ p 2)))
            n (if (= vs "") nil (distof vs)))
      (if (and (/= k "") n (numberp n)) (cons k n) nil))
    nil))

;; 读 INI → ((节名 (键 . 值)...) ...); 文件不存在/读失败返回 nil
(defun dt:jrt-cfg-read (path / f ln sec ent tmp secs)
  (setq secs nil sec nil)
  (vl-catch-all-apply
    '(lambda ( )
       (setq f (open path "r"))
       (if f
         (progn
           (while (setq ln (read-line f))
             (setq ln (vl-string-trim " \t\r" ln))
             (cond
               ((= ln "") nil)
               ((member (substr ln 1 1) '(";" "#")) nil)
               ((= (substr ln 1 1) "[")
                ;; v9.13: 原用 (- (strlen ln) 2) 取长度 —— AutoCAD 2021 之前
                ;;   strlen 按字节计而 substr 按字符计, 中文节名(如 "[通用一]")
                ;;   会连带尾部 "]"(变成 "通用一]")导致配置节永远匹配不上。
                (setq sec (vl-string-trim " \t[]" (substr ln 2))))
               ((setq ent (dt:jrt-cfg-kv ln))
                (if (and sec (/= sec ""))
                  (progn
                    (setq tmp (vl-remove (assoc (car ent) (cdr (assoc sec secs)))
                                         (cdr (assoc sec secs)))
                          tmp (cons ent tmp)
                          secs (cons (cons sec tmp)
                                     (vl-remove (assoc sec secs) secs))))))))
           (close f)
           (setq f nil))))
    nil)
  ;; v9.14: 异常兜底关闭 —— 读行中途出错时句柄不再滞留
  (if f (progn (vl-catch-all-apply 'close (list f)) (setq f nil)))
  (reverse secs))

;; 数据 → 指定节的键值表(无该节 nil)
(defun dt:jrt-cfg-sec (data sec / e)
  (if (and data (setq e (assoc sec data))) (cdr e)))

;; 节内取键值(无该键 nil; 值可为 0, 0 非 nil 仍算"有")
(defun dt:jrt-cfg-get (data sec key)
  (cdr (assoc key (dt:jrt-cfg-sec data sec))))

;; 当前模板的参数默认值: ini 配置节 → 模板内置默认表 → dt:jrt-param-table caddr
(defun dt:jrt-param-default (key / tpl v)
  (setq tpl (dt:jrt-template-row))
  (cond ((setq v (dt:jrt-cfg-get *jrt-cfg* (car tpl) key)) v)
        ((cdr (assoc key (nth 2 tpl))))
        (T (caddr (assoc key dt:jrt-param-table)))))

;; 首次自动生成配置文件(按模板分节 + 中文注释标签)
(defun dt:jrt-cfg-gen (path / f tpl kv lbl)
  (vl-catch-all-apply
    '(lambda ( )
       (setq f (open path "w"))
       (if f
         (progn
           (write-line "; jrt_runner 参数默认值配置(首次运行自动生成, 记事本可改)" f)
           (write-line "; 按模板分节; 改数值保存后, 下次打开模板/参数窗口即生效(无需重载)" f)
           (write-line "; 恢复默认按钮 = 本文件的值; 删除本文件 = 回代码内置默认" f)
           (write-line "; 上次填的值在 jrt_runner_mem.ini(程序自动维护, 一般不用管)" f)
           (write-line "" f)
           (foreach tpl dt:jrt-template-table
             (write-line (strcat "[" (car tpl) "]") f)
             (foreach kv (nth 2 tpl)
               (setq lbl (cdr (assoc (car kv) dt:jrt-param-labels)))
               (if lbl (write-line (strcat "; " lbl) f))
               (write-line (strcat (car kv) " = " (rtos (cdr kv) 2 4)) f))
             (write-line "" f))
           (close f)
           (setq f nil))))
    nil)
  (if f (progn (vl-catch-all-apply 'close (list f)) (setq f nil)))
  T)

;; 确定参数框后保存当前模板的上次值(每模板各一套; 只存该模板可见键)
(defun dt:jrt-mem-save ( / name keys vals path sc f kv)
  (setq name (car (dt:jrt-template-row))
        keys (dt:jrt-tpl-keys)
        vals (mapcar '(lambda (k) (cons k (eval (cadr (assoc k dt:jrt-param-table)))))
                     keys))
  (setq *jrt-mem* (cons (cons name vals)
                        (vl-remove (assoc name *jrt-mem*) *jrt-mem*))
        path (strcat (dt:jrt-cfg-dir) "\\jrt_runner_mem.ini"))
  (vl-catch-all-apply
    '(lambda ( )
       (setq f (open path "w"))
       (if f
         (progn
           (write-line "; jrt_runner 参数记忆(确定参数窗口时自动更新, 可删除)" f)
           (write-line "[模板]" f)
           (write-line (strcat "template = " (itoa *jrt-template*)) f)
           (write-line "" f)
           (foreach sc *jrt-mem*
             ;; v9.13: 跳过 "[模板]" 节(上方已单独写出)—— 否则会重复写出
             (if (/= (car sc) "模板")
               (progn
                 (write-line (strcat "[" (car sc) "]") f)
                 (foreach kv (cdr sc)
                   (write-line (strcat (car kv) " = " (rtos (cdr kv) 2 4)) f))
                 (write-line "" f))))
           (close f)
           (setq f nil))))
    nil)
  (if f (progn (vl-catch-all-apply 'close (list f)) (setq f nil)))
  (princ))

;; 加载末尾调用: 生成缺失配置 + 恢复上次模板与该模板的上次参数值
(defun dt:jrt-cfg-boot ( / path idx)
  (vl-catch-all-apply
    '(lambda ( )
       (setq path (strcat (dt:jrt-cfg-dir) "\\jrt_runner.ini"))
       (setq *jrt-cfg* (dt:jrt-cfg-read path))
       (if (null *jrt-cfg*)
         (progn
           (dt:jrt-cfg-gen path)
           (setq *jrt-cfg* (dt:jrt-cfg-read path))))
       (setq *jrt-mem*
             (dt:jrt-cfg-read (strcat (dt:jrt-cfg-dir) "\\jrt_runner_mem.ini")))
       (setq idx (dt:jrt-cfg-get *jrt-mem* "模板" "template"))
       (if (and idx (numberp idx)
                (>= (fix idx) 0) (< (fix idx) (length dt:jrt-template-table)))
         (progn
           (setq *jrt-template* (fix idx)
                 *jrt-tpl-pick* (fix idx))
           (dt:jrt-apply-template (fix idx) T))))
    nil)
  (princ))

;; ============================================================================
;; 加热条模板注册表(v9.8, v9.9 扩展) —— 多套规则模板, JRT 执行时先弹独立选择框
;; 每行: (名称 说明 参数默认表 环节覆盖表)
;;   参数默认表: 该模板用到的参数键点对表(键为字符串, 与参数框控件同名;
;;               v9.9 由符号改字符串 —— 原符号键使 apply-template 的
;;               assoc 永远失配, 模板参数默认从未生效; 选择模板时写入
;;               全局变量, 参数框只显示这些键, "恢复默认"也回退这张表)
;;   环节覆盖表: 可覆盖 4 个环节 + 1 个主流程, 形如 ((decide . 函数)
;;               (cap-circle . 函数) (cap-line . 函数) (build . 函数)
;;               (process . 函数)); 前四者覆盖函数签名须与默认函数完全一致;
;;               process 覆盖后整个主流程由该函数自管(无参, 不走内置 LD
;;               流程, c:JRT 内直接调用); nil = 全部用默认环节
;; 新增模板: 在表中加一行(必要时新增覆盖函数 defun), 交付新版本。
;; ============================================================================
(setq dt:jrt-template-table
      (list
        (list "通用一"
              "端帽按相邻通道内壁间距判定(RZ整圆帽/封闭线圆弧帽)"
              '(("jrt_offset" . 29.0) ("jrt_cap_inset" . 11.0) ("jrt_fillet_r" . 19.0)
                ("jrt_cap_r" . 29.0) ("jrt_inner_step" . 4.0) ("jrt_inner_count" . 2.0))
              nil)
        (list "通用二"
              "JRT外壁整圈+JRTDW标记出线口→内偏恒朝轮廓内侧(几何判定,与JRTDW画向无关); 颈线恒朝FLB外侧不入侵; 圆弧壁通道线自动延伸"
              '(("jrt2_half_w" . 16.5) ("jrt2_end_r" . 12.0) ("jrt2_hook_ext" . 5.0)
                ("jrt_inner_step" . 4.0) ("jrt_inner_count" . 2.0)
                ("jrt2_neck_len" . 65.0) ("jrt2_neck_off" . 35.0)
                ("jrt2_close_r" . 15.0) ("jrt2_trim_r" . 15.0))
              '((process . dt:jrt2-process)))))
(setq *jrt-template* 0)   ; 当前选中模板下标(选择框确定后更新)
(setq *jrt-tpl-pick* 0)   ; 选择框单选过程中的临时下标(回调写入)
(setq *jrt2-made* nil)    ; 两点式上一轮产物句柄表(重跑先删; 句柄跨存盘有效)

;; ============================================================================
;; 一、工具函数(与主脚本 flb_runner v9.5 逐字一致)
;; ============================================================================
;; 计算两点距离
(defun dt:dist (p1 p2)
  (sqrt (+ (expt (- (car p1) (car p2)) 2)
           (expt (- (cadr p1) (cadr p2)) 2)
           (expt (- (caddr p1) (caddr p2)) 2))))

;; 把平铺坐标列表 (x1 y1 z1 x2 y2 z2 ...) 转成点列表 ((x1 y1 z1) (x2 y2 z2) ...)
(defun dt:flat->pts (lst / pts)
  (setq pts nil)
  (while lst
    (setq pts (cons (list (car lst) (cadr lst) (caddr lst)) pts)
          lst (cdddr lst)))
  (reverse pts))

;; 求两个 VLA 对象的交点列表 (不延伸)
;; 必须用 vla-intersectwith(返回类型固定的 Variant), 不要用 vlax-invoke
(defun dt:inters-pts (o1 o2 / v arr)
  (setq v (vl-catch-all-apply 'vla-intersectwith (list o1 o2 0)))
  (if (not (vl-catch-all-error-p v))
    (progn
      (setq arr (vl-catch-all-apply
                  'vlax-safearray->list (list (vlax-variant-value v))))
      (if (not (vl-catch-all-error-p arr))
        (dt:flat->pts arr)
        nil))
    nil))

;; 选择集 -> 图元名列表
(defun dt:ss->list (ss / i lst)
  (setq i 0 lst nil)
  (repeat (sslength ss)
    (setq lst (cons (ssname ss i) lst)
          i (1+ i)))
  (reverse lst))

;; 当前文档模型空间(集中获取, 避免各函数重复拼 vla-get 链)
(defun dt:ms ()
  (vla-get-modelspace (vla-get-activedocument (vlax-get-acad-object))))

;; 选中指定图层全部对象并转为 VLA 对象列表(图层为空返回 nil)
(defun dt:layer-vlas (layer / ss)
  (setq ss (ssget "X" (list (cons 8 layer))))
  (if ss
    (mapcar 'vlax-ename->vla-object (dt:ss->list ss))))

;; 取多段线的全部顶点(3D点列表)
(defun dt:poly-pts (obj / coords is-2d n i pts)
  (setq coords (vlax-safearray->list (vlax-variant-value (vla-get-coordinates obj)))
        is-2d   (member (vla-get-objectname obj) '("AcDbLWPolyline" "AcDbPolyline")))
  (if is-2d
    (setq n (/ (length coords) 2))
    (setq n (/ (length coords) 3)))
  (setq i 0 pts nil)
  (repeat n
    (if is-2d
      (setq pts (cons (list (nth (* i 2) coords)
                            (nth (1+ (* i 2)) coords)
                            0.0) pts))
      (setq pts (cons (list (nth (* i 3) coords)
                            (nth (1+ (* i 3)) coords)
                            (nth (+ 2 (* i 3)) coords)) pts)))
    (setq i (1+ i)))
  (reverse pts))

;; 直线上按"到起点距离"取点: sp=起点 ep=终点 d=距离 total=总长
(defun dt:point-on-line (sp ep d total / k)
  (if (> total 1e-9)
    (progn
      (setq k (/ d total))
      (list (+ (car sp) (* k (- (car ep) (car sp))))
            (+ (cadr sp) (* k (- (cadr ep) (cadr sp))))
            (+ (caddr sp) (* k (- (caddr ep) (caddr sp))))))
    sp))

;; 已排序的数值列表按容差去重
(defun dt:uniq (lst tol / r x)
  (setq r nil)
  (foreach x lst
    (if (or (null r) (> (- x (car r)) tol))
      (setq r (cons x r))))
  (reverse r))

;; eName 排除判定: 对象 obj 是否在 eName 列表 exclude 中
;; (v8.14 关键坑: vla-object 每次转换生成新实例, 跨函数 equal 恒不成立,
;;  对象身份比较必须用 eName)
(defun dt:excluded-p (obj exclude)
  (vl-some '(lambda (x) (equal x (vlax-vla-object->ename obj)))
           exclude))

;; v9.14: 实体是否为可求端点/曲线参数的曲线(直线/弧/多段线) —— 文字/块等
;; 混入源图层时 vlax-curve 系列会抛"参数类型错误"中断流程, 收集/迭代前
;; 一律先过本判定
(defun dt:curve-p (obj / tp)
  (setq tp (vl-catch-all-apply 'vla-get-objectname (list obj)))
  (if (vl-catch-all-error-p tp)
    nil
    (member tp '("AcDbLine" "AcDbArc" "AcDbLWPolyline" "AcDbPolyline"))))

;; v9.14: 列表过滤, 只留 dt:curve-p 为真的实体
(defun dt:curves-only (vla-list)
  (vl-remove-if '(lambda (o) (not (dt:curve-p o))) vla-list))

;; 点相对圆心的角度, 归一化到 [start-a, start-a+2pi)
(defun dt:norm-angle (pt center start-a / a)
  (setq a (angle (list (car center) (cadr center)) (list (car pt) (cadr pt))))
  (if (< a start-a) (setq a (+ a (* 2 pi))))
  (if (>= a (+ start-a (* 2 pi))) (setq a (- a (* 2 pi))))
  a)

;; 判断点是否位于某条流道线的带状区域内
;; (即: 该点到最近一条流道中心线的距离 < 偏移距离 - 容差)
(defun dt:in-zone (pt center-lines off-dist / d cp cl)
  (setq d 1e30)
  (foreach cl center-lines
    (setq cp (vl-catch-all-apply 'vlax-curve-getclosestpointto (list cl pt)))
    (if (not (vl-catch-all-error-p cp))
      (setq d (min d (distance pt cp)))))
  (< d (- off-dist 1e-3)))

;; ===================== 向量工具 =====================

;; 向量单位化(零向量原样返回)
(defun dt:unit (v / l)
  (setq l (sqrt (+ (* (car v) (car v))
                   (* (cadr v) (cadr v))
                   (* (caddr v) (caddr v)))))
  (if (> l 1e-12)
    (list (/ (car v) l) (/ (cadr v) l) (/ (caddr v) l))
    v))

;; 点 + 方向向量 * 标量
(defun dt:pt+vec (p v s)
  (list (+ (car p) (* (car v) s))
        (+ (cadr p) (* (cadr v) s))
        (+ (caddr p) (* (caddr v) s))))

;; 反余弦 (AutoLISP 无内置 acos)
(defun dt:acos (c / cc)
  (setq cc c)
  (if (> cc 1.0) (setq cc 1.0))
  (if (< cc -1.0) (setq cc -1.0))
  (if (>= cc 1.0) 0.0
    (if (<= cc -1.0) pi
      (atan (sqrt (- 1.0 (* cc cc))) cc))))

;; 正切 (AutoLISP 无内置 tan)
(defun dt:tan (a)
  (/ (sin a) (cos a)))

;; 两个方向向量之间的夹角(弧度, 0 ~ pi)
(defun dt:angle-between (d1 d2 / l1 l2 dot)
  (setq l1 (sqrt (+ (* (car d1) (car d1))
                    (* (cadr d1) (cadr d1))
                    (* (caddr d1) (caddr d1))))
        l2 (sqrt (+ (* (car d2) (car d2))
                    (* (cadr d2) (cadr d2))
                    (* (caddr d2) (caddr d2))))
        dot (+ (* (car d1) (car d2))
               (* (cadr d1) (cadr d2))
               (* (caddr d1) (caddr d2))))
  (if (and (> l1 1e-12) (> l2 1e-12))
    (dt:acos (/ dot (* l1 l2)))
    0.0))

;; 判断两个方向是否不平行(夹角在 0.05 ~ pi-0.05 之外视为平行)
(defun dt:not-parallel (d1 d2 / ang)
  (setq ang (dt:angle-between d1 d2))
  (and (> ang 0.05) (< ang (- pi 0.05))))

;; 取曲线两端头信息: 返回 ((起点 起点指向主体方向) (终点 终点指向主体方向))
;; 方向均指向"曲线主体"内部, 用于圆角计算
(defun dt:end-infos (obj / sp ep sd ed)
  (setq sp (vlax-curve-getstartpoint obj)
        ep (vlax-curve-getendpoint obj)
        sd (dt:unit (vlax-curve-getfirstderiv obj (vlax-curve-getstartparam obj)))
        ed (dt:unit (vlax-curve-getfirstderiv obj (vlax-curve-getendparam obj))))
  ;; 终点处一阶导数指向曲线延伸方向, 取反使其指向主体
  (setq ed (list (- (car ed)) (- (cadr ed)) (- (caddr ed))))
  (list (list sp sd) (list ep ed)))

;; 把曲线的一个端头移动到新位置(直线改端点, 圆弧改角度, 多段线改顶点)
;; v7.11: 增加圆弧支持 —— 圆弧的 StartPoint/EndPoint 是只读属性,
;;  vla-put-startpoint 对 AcDbArc 无效(静默失败), 导致圆弧端头修剪失效,
;;  圆角弧"单独加上去"(残余线未剪)。改为设置 StartAngle/EndAngle。
(defun dt:set-endpoint (obj et pt / is-poly is-arc c r ang n)
  (setq is-poly (= (vla-get-objectname obj) "AcDbPolyline")
        is-arc  (= (vla-get-objectname obj) "AcDbArc"))
  (cond
    (is-poly
     (if (= et "S")
       (vla-put-coordinate obj 0 (vlax-3d-point pt))
       (progn
         (setq n (vla-get-numberofvertices obj))
         (vla-put-coordinate obj (1- n) (vlax-3d-point pt)))))
    (is-arc
     ;; 圆弧: 端头移动到"圆心指向 pt 的角度"处(在弧半径上)
     (setq c (vlax-safearray->list (vlax-variant-value (vla-get-center obj)))
           r (vla-get-radius obj)
           ang (angle (list (car c) (cadr c)) (list (car pt) (cadr pt))))
     (if (= et "S")
       (vla-put-startangle obj ang)
       (vla-put-endangle obj ang)))
    (T
     (if (= et "S")
       (vla-put-startpoint obj (vlax-3d-point pt))
       (vla-put-endpoint obj (vlax-3d-point pt))))))

;; 返回曲线上"从指定端头沿曲线向内走 dist 距离"的点(保证在曲线上!)
;; v7.16 关键修复: 圆角/倒角的切点必须用"沿曲线走"而非"切线方向外推"。
(defun dt:endpoint-in (obj et dist / total)
  (setq total (vlax-curve-getdistatparam obj (vlax-curve-getendparam obj)))
  (if (= et "S")
    (vlax-curve-getpointatdist obj (min dist total))
    (vlax-curve-getpointatdist obj (max 0.0 (- total dist)))))

;; ============================================================================
;; 二、切割重建链(与主脚本逐字一致; cut-curve/trim-curve 改名 dt:jrt-*:
;; cx_runner 的 dt:cut-curve 默认图层不同, 三脚本同时加载时避免互相覆盖)
;; ============================================================================

;; 类型分发: 交点列表 -> 排序去重后的切割参数列表(首 0, 尾全长)
(defun dt:cut-params (obj others-pts / obj-type sp ep total center start-a end-param
                      cut)
  (setq obj-type (vla-get-objectname obj))
  (cond
    ((= obj-type "AcDbLine")
     (setq sp (vlax-safearray->list (vlax-variant-value (vla-get-startpoint obj)))
           ep (vlax-safearray->list (vlax-variant-value (vla-get-endpoint obj)))
           total (dt:dist sp ep))
     (append (list 0.0)
             (dt:uniq (vl-sort (mapcar '(lambda (p) (dt:dist p sp)) others-pts) '<) 1e-6)
             (list total)))
    ((= obj-type "AcDbArc")
     (setq center (vlax-safearray->list (vlax-variant-value (vla-get-center obj)))
           start-a (vla-get-startangle obj)
           end-param (vla-get-endangle obj))
     (if (< end-param start-a) (setq end-param (+ end-param (* 2 pi))))
     (setq cut (dt:uniq (vl-sort (mapcar '(lambda (p) (dt:norm-angle p center start-a))
                                         others-pts) '<) 1e-6)
           cut (mapcar '(lambda (a) (- a start-a)) cut))
     (append (list 0.0) cut (list (- end-param start-a))))
    (T ; 多段线: 参数 = 顶点索引 + 段内比例
     ;; v9.14: 交点浮点偏移曲线时 getparamatpoint 可能返回 nil(甚至抛错),
     ;;   先 catch 求值并剔除 nil 再排序 —— nil 进 vl-sort 报 bad argument
     (append (list 0.0)
             (dt:uniq (vl-sort
                        (vl-remove-if 'null
                          (mapcar '(lambda (p) (vl-catch-all-apply
                                                 'vlax-curve-getparamatpoint
                                                 (list obj p)))
                                  others-pts))
                        '<) 1e-6)
             (list (vlax-curve-getendparam obj))))))

;; 类型分发: 段中点(用于裁剪模式的区域判断)
(defun dt:seg-mid (obj t1 t2 / obj-type sp ep total center radius start-a m)
  (setq obj-type (vla-get-objectname obj))
  (cond
    ((= obj-type "AcDbLine")
     (setq sp (vlax-safearray->list (vlax-variant-value (vla-get-startpoint obj)))
           ep (vlax-safearray->list (vlax-variant-value (vla-get-endpoint obj)))
           total (dt:dist sp ep))
     (dt:point-on-line sp ep (/ (+ t1 t2) 2.0) total))
    ((= obj-type "AcDbArc")
     (setq center (vlax-safearray->list (vlax-variant-value (vla-get-center obj)))
           radius (vla-get-radius obj)
           start-a (vla-get-startangle obj)
           m (polar center (+ start-a (/ (+ t1 t2) 2.0)) radius))
     (list (car m) (cadr m) (caddr center)))
    (T (vlax-curve-getpointatparam obj (/ (+ t1 t2) 2.0)))))

;; 类型分发: 按参数区间 [t1, t2] 重建一段, 放入 layer(返回新对象或 nil)
(defun dt:rebuild-seg (obj t1 t2 layer / obj-type sp ep total p1 p2 center radius
                       start-a new-obj is-2d)
  (setq obj-type (vla-get-objectname obj)
        new-obj nil)
  (cond
    ((= obj-type "AcDbLine")
     (setq sp (vlax-safearray->list (vlax-variant-value (vla-get-startpoint obj)))
           ep (vlax-safearray->list (vlax-variant-value (vla-get-endpoint obj)))
           total (dt:dist sp ep)
           p1 (dt:point-on-line sp ep t1 total)
           p2 (dt:point-on-line sp ep t2 total))
     (setq new-obj (vla-addline (dt:ms) (vlax-3d-point p1) (vlax-3d-point p2))))
    ((= obj-type "AcDbArc")
     (setq center (vlax-safearray->list (vlax-variant-value (vla-get-center obj)))
           radius (vla-get-radius obj)
           start-a (vla-get-startangle obj))
     (setq new-obj (vla-addarc (dt:ms) (vlax-3d-point center) radius
                               (+ start-a t1) (+ start-a t2))))
    (T
     (setq is-2d (member obj-type '("AcDbLWPolyline" "AcDbPolyline")))
     (setq new-obj (dt:poly-rebuild obj t1 t2 (dt:poly-pts obj) is-2d))))
  (if new-obj (vla-put-layer new-obj layer))
  new-obj)

;; 按参数区间 [t1, t2] 重建多段线
(defun dt:poly-rebuild (obj t1 t2 vtx is-2d / new-pts i nv flat ms pt)
  (setq new-pts (list (vlax-curve-getpointatparam obj t1))
        nv (length vtx)
        i 0)
  (while (< i nv)
    (if (and (> i (+ t1 1e-6)) (< i (- t2 1e-6)))
      (setq new-pts (append new-pts (list (nth i vtx)))))
    (setq i (1+ i)))
  (setq new-pts (append new-pts (list (vlax-curve-getpointatparam obj t2))))
  (setq flat nil)
  (foreach pt new-pts
    (if is-2d
      (setq flat (append flat (list (car pt) (cadr pt))))
      (setq flat (append flat (list (car pt) (cadr pt) (caddr pt))))))
  (setq ms (dt:ms))
  (if is-2d
    (vla-addlightweightpolyline
      ms
      (vlax-make-variant
        (vlax-safearray-fill
          (vlax-make-safearray vlax-vbDouble (cons 0 (1- (length flat))))
          flat)
        (logior vlax-vbArray vlax-vbDouble)))
    (vla-addpolyline
      ms
      (vlax-make-variant
        (vlax-safearray-fill
          (vlax-make-safearray vlax-vbDouble (cons 0 (1- (length flat))))
          flat)
        (logior vlax-vbArray vlax-vbDouble)))))

;; 通用切割驱动(裁剪模式; 主体与主脚本一致):
;;   把曲线按交点切成小段 -> 段中点落流道带状区域内(center-lines, 宽
;;   off-dist)的段删除 -> 保留段重建为新对象(放指定图层), 删原对象。
(defun dt:jrt-cut-curve (obj others-pts layer center-lines off-dist mode /
                     obj-type cut t-end i t1 t2 keep-segs closed-p seg)
  (if (null layer) (setq layer "JRT"))
  (if (null others-pts)
    nil
    (progn
      (setq obj-type (vla-get-objectname obj))
      (cond
        ((not (member obj-type '("AcDbLine" "AcDbArc"
                                 "AcDbLWPolyline" "AcDbPolyline")))
         (princ (strcat "\n  跳过: " obj-type " 暂不支持切割处理。"))
         nil)
        ((and (member obj-type '("AcDbLWPolyline" "AcDbPolyline"))
              (progn
                (setq closed-p (vl-catch-all-apply 'vla-get-closed (list obj)))
                (and (not (vl-catch-all-error-p closed-p)) (< closed-p 0))))
         (princ "\n  跳过: 闭合多段线。")
         nil)
        (T
         (setq cut (dt:cut-params obj others-pts)
               t-end (last cut)
               keep-segs nil i 0)
         (while (< i (1- (length cut)))
           (setq t1 (nth i cut)
                 t2 (nth (1+ i) cut))
           (if (> (- t2 t1) 1e-9)
             (if (or (null mode)
                     (not (dt:in-zone (dt:seg-mid obj t1 t2)
                                      center-lines off-dist)))
               (setq keep-segs (cons (list t1 t2) keep-segs))))
           (setq i (1+ i)))
         (setq keep-segs (reverse keep-segs))
         (cond
           ;; 整条线都在区域内: 删除
           ((null keep-segs) (vla-delete obj) T)
           ;; 仅一段且覆盖全长: 保持原样
           ((and (= (length keep-segs) 1)
                 (< (abs (caar keep-segs)) 1e-6)
                 (< (abs (- (cadar keep-segs) t-end)) 1e-6))
            T)
           ;; 重建保留段, 删除原线
           (T
            (foreach seg keep-segs
              (dt:rebuild-seg obj (car seg) (cadr seg) layer))
            (vla-delete obj)
            T)))))))

;; 区域裁剪分发(改名隔离, 见 dt:jrt-cut-curve 说明)
(defun dt:jrt-trim-curve (obj others-pts center-lines off-dist layer)
  (dt:jrt-cut-curve obj others-pts layer center-lines off-dist "TRIM"))

;; boundingbox 输出解包: vla-getboundingbox 的输出参数有的版本绑定为
;; safearray 本体, 有的为 variant(内含 safearray) —— 统一容忍两种
;; (与 flb_runner 逐字一致; v9.14 供 cross-points 包围盒预过滤用)
(defun dt:rect-bb-pts (x)
  (if (= (type x) 'variant)
    (vlax-safearray->list (vlax-variant-value x))
    (vlax-safearray->list x)))

;; 对象列表整体范围: 返回 (minx miny maxx maxy), 全部失败返回 nil
(defun dt:rect-bbox (objs / o mn mx p minx miny maxx maxy)
  (foreach o objs
    (setq mn nil mx nil)
    (if (not (vl-catch-all-error-p
               (vl-catch-all-apply 'vla-getboundingbox (list o 'mn 'mx))))
      (progn
        (setq p (dt:rect-bb-pts mn))
        (setq minx (if minx (min minx (car p)) (car p))
              miny (if miny (min miny (cadr p)) (cadr p)))
        (setq p (dt:rect-bb-pts mx))
        (setq maxx (if maxx (max maxx (car p)) (car p))
              maxy (if maxy (max maxy (cadr p)) (cadr p))))))
  (if (and minx miny maxx maxy) (list minx miny maxx maxy) nil))

;; 两包围盒 (minx miny maxx maxy) 是否相交(含接触);
;; 任一为 nil(取盒失败)时按相交处理, 不跳过求交 —— 保守不漏
(defun dt:bbox-overlap-p (a b)
  (if (or (null a) (null b))
    T
    (and (<= (car a) (caddr b)) (>= (caddr a) (car b))
         (<= (cadr a) (cadddr b)) (>= (cadddr a) (cadr b)))))

;; 列表内所有线两两求交(不延伸), 返回 ((对象 该对象的交点列表) ...), 顺序与入序一致
;; v9.14: 包围盒预过滤 —— 每对象只取一次 boundingbox(dt:rect-bbox), 两盒
;;   不相交则跳过 COM 求交(bbox 不相交 ⇒ 两曲线必无交点, 结果不变);
;;   大图上把 O(n²) 次 intersectwith 降为相邻对数量级(压力场景提速)
(defun dt:cross-points (vla-list / pts-pairs pair rec obj b1 pts other o)
  (setq pts-pairs nil
        pair nil)
  (setq pair (mapcar '(lambda (o bb) (list o bb))
                     vla-list
                     (mapcar '(lambda (o) (dt:rect-bbox (list o))) vla-list)))
  (foreach rec pair
    (setq obj (car rec) b1 (cadr rec) pts nil)
    (foreach other pair
      (setq o (car other))
      (if (and (not (equal o obj))
               (dt:bbox-overlap-p b1 (cadr other)))
        (setq pts (append pts (dt:inters-pts obj o)))))
    (setq pts-pairs (cons (cons obj pts) pts-pairs)))
  (reverse pts-pairs))

;; ============================================================================
;; 三、断口圆角(主体与主脚本逐字一致, 改名 dt:jrt-fillet-pair:
;; cx_runner 的 dt:cx-fillet-pair 多一个 nochk 第7参, 三脚本同时加载时
;; 6/7 参定义互相覆盖会报参数数量错误)
;; ============================================================================

;; 处理一个断口对: 计算圆角几何, 递减半径, 方向验证, 修剪两线, 创建圆角弧, 必要时标注
;; h1/h2 = (对象 端类型"S"/"E" 端头点 指向主体方向)
;; layer = 圆角弧/标注文字所在图层
;; r-start = 圆角起始半径
;; 返回: (实际半径 T) 表示成功, nil 表示失败
(defun dt:jrt-fillet-pair (h1 h2 center-lines off-dist layer r-start / obj1 et1 p1 d1 obj2 et2 p2 d2
                       ang2 b1 b2 done r d-tan len1 len2 c t1 t2 m a1 a2
                       tmp arc txt txt-pt ms ok)
  (if (null layer) (setq layer "JRT"))
  (if (null r-start) (setq r-start *jrt-fillet-r*))
  (setq obj1 (car h1) et1 (cadr h1) p1 (caddr h1) d1 (cadddr h1)
        obj2 (car h2) et2 (cadr h2) p2 (caddr h2) d2 (cadddr h2))
  ;; 两切线方向夹角的一半
  (setq ang2 (/ (dt:angle-between d1 d2) 2.0))
  ;; 圆心候选方向: b1 = 角平分线(圆心在断口外侧=区域外, A方案)
  ;;               b2 = 补角平分线(备用, 方向反了时换用)
  (setq b1 (dt:unit (mapcar '+ d1 d2)))
  (setq b2 (dt:unit (mapcar '- d1 d2)))
  ;; 半径递减尝试: r-start -> 1, 要求切点不超出线的当前长度
  (setq done nil r r-start)
  (while (and (not done) (> r 0))
    (setq len1 (vlax-curve-getdistatparam obj1 (vlax-curve-getendparam obj1))
          len2 (vlax-curve-getdistatparam obj2 (vlax-curve-getendparam obj2))
          d-tan (/ r (dt:tan ang2)))
    (if (and (<= d-tan len1) (<= d-tan len2))
      (setq done T)
      (setq r (1- r))))
  (if (not done)
    nil
    (progn
      ;; 先按 b1 方向算圆心(区域外), 若侵入则换 b2
      (setq c (dt:pt+vec p1 b1 (/ r (sin ang2))))
      (if (dt:in-zone c center-lines off-dist)
        (progn
          (setq c (dt:pt+vec p1 b2 (/ r (sin ang2))))
          (if (dt:in-zone c center-lines off-dist)
            (setq ok nil)
            (setq ok T)))
        (setq ok T))
      (if (null ok)
        nil
        (progn
          ;; 切点(v7.16: 沿曲线走 d-tan, 保证在线上——圆弧线也精确连接)
          (setq t1 (dt:endpoint-in obj1 et1 d-tan)
                t2 (dt:endpoint-in obj2 et2 d-tan)
                ;; 弧中点(圆心朝断口方向偏移 r)
                m (dt:pt+vec c (dt:unit (mapcar '- p1 c)) r))
          ;; 修剪两条线的端头到切点
          (dt:set-endpoint obj1 et1 t1)
          (dt:set-endpoint obj2 et2 t2)
          ;; 创建圆角弧: 保证从 a1 逆时针到 a2 的弧为劣弧(弧长<=180°)
          (setq ms (dt:ms)
                a1 (angle (list (car c) (cadr c)) (list (car t1) (cadr t1)))
                a2 (angle (list (car c) (cadr c)) (list (car t2) (cadr t2))))
          (if (> (if (> a2 a1) (- a2 a1) (+ (- a2 a1) (* 2 pi))) pi)
            (setq tmp a1 a1 a2 a2 tmp))
          (setq arc (vla-addarc ms (vlax-3d-point c) r a1 a2))
          (vla-put-layer arc layer)
          ;; 实际半径小于起始半径 r-start 时, 在圆角旁标注文字(字高 10)
          (if (< r r-start)
            (progn
              (setq txt-pt (dt:pt+vec m b1 14.0))
              (setq txt (vla-addtext ms (strcat "R" (rtos r 2 0))
                                     (vlax-3d-point txt-pt) 10.0))
              (vla-put-height txt 10.0)
              (vla-put-layer txt layer)))
          (list r T))))))

;; 收集 VLA 列表内所有线端头(可按 eName 列表排除):
;; 返回 ((对象 端类型"S"/"E" 端头点 指向主体方向) ...)
;; v9.14: 先按 dt:curve-p 过滤(文字等非曲线实体的端点查询会抛错)
(defun dt:collect-heads (vla-list exclude / heads infos obj)
  (setq heads nil)
  (foreach obj vla-list
    (if (and (not (dt:excluded-p obj exclude))
             (dt:curve-p obj))
      (progn
        (setq infos (dt:end-infos obj))
        (setq heads (append heads
          (list (list obj "S" (caar infos) (cadar infos))
                (list obj "E" (caadr infos) (cadadr infos))))))))
  heads)

;; 端头两两配对: 端头重合(<1e-3, 即断口) + 不同对象 + 切线方向不平行
(defun dt:pair-heads (heads / pairs i j h1 h2)
  (setq pairs nil i 0)
  (foreach h1 heads
    (setq j 0)
    (foreach h2 heads
      (if (> j i)
        (if (and (<= (dt:dist (caddr h1) (caddr h2)) 1e-3)
                 (not (equal (car h1) (car h2)))
                 (dt:not-parallel (cadddr h1) (cadddr h2)))
          (setq pairs (cons (list h1 h2) pairs))))
      (setq j (1+ j)))
    (setq i (1+ i)))
  pairs)

;; ============================================================================
;; 四、图层与偏移(与主脚本逐字一致)
;; ============================================================================

;; 确保图层存在: 不存在则创建并设颜色; 已存在则把颜色校正为登记色
;; (v9.34 起配色统一: 三脚本登记表同值, 每次运行对齐, 老图自动刷新色)。
;; v9.5: AutoCAD 图层名不区分大小写 —— 若已存在图层与请求写法大小写不一致
;;       (如已有小写 "jrt"), 自动改名为请求写法("JRT"), 图上对象全部跟随。
(defun dt:ensure-layer (layers name color cname / obj ent actual)
  (setq ent (tblsearch "LAYER" name))
  (if (null ent)
    (progn
      (setq obj (vla-add layers name))
      (vla-put-color obj color)
      (princ (strcat "\n已创建新图层 \"" name "\" (" cname ")。"))
      obj)
    (progn
      (setq actual (cdr (assoc 2 ent)))
      (if (not (equal actual name))
        (progn
          (vl-catch-all-apply 'vla-put-name (list (vla-item layers actual) name))
          (princ (strcat "\n图层 \"" actual "\" 已改名为 \"" name "\"。"))))
      (setq obj (vl-catch-all-apply 'vla-item (list layers name)))
      (if (and (not (vl-catch-all-error-p obj)) obj
               (/= (vl-catch-all-apply 'vla-get-color (list obj)) color))
        (vla-put-color obj color))
      (princ (strcat "\n图层 \"" name "\" 已存在, 颜色已对齐登记值(" cname ")。"))
      nil)))

;; 删除指定图层上的所有对象(保留图层定义), 用于重跑时清除上一轮产物
(defun dt:purge-layer (lname / s n i obj)
  (setq s (ssget "X" (list (cons 8 lname))))
  (if s
    (progn
      (setq n (sslength s) i 0)
      (repeat n
        (setq obj (vlax-ename->vla-object (ssname s i)))
        (vl-catch-all-apply 'vla-delete (list obj))
        (setq i (1+ i)))
      n)
    0))

;; 只偏移指定图元(eName 列表), 用于出线槽: 只偏移源线, 避免重跑 OFF 时
;; 把"CX"(出线槽)图层里上一次残留的通道壁/圆角弧再偏移一遍(重跑污染)。v8.14
;; v9.1: 偏移循环唯一化 —— dt:offset-layer = 全选图层后调本函数
(defun dt:offset-enames (enames new-layer dist / i ent ent-obj obj-type
                         r1 r2 o1 o2 new-obj ok skip)
  (setq ok 0 skip 0 i 0)
  (foreach ent enames
    (if (and ent (/= ent ""))
      (progn
        (setq ent-obj (vlax-ename->vla-object ent)
              obj-type (vla-get-objectname ent-obj))
        ;; 仅处理支持偏移的对象类型(直线/多段线/圆弧/圆/椭圆/样条)
        (if (member obj-type
                    '("AcDbLine" "AcDbLWPolyline" "AcDbPolyline"
                      "AcDbArc" "AcDbCircle" "AcDbEllipse" "AcDbSpline"))
          (progn
            ;; 分别用正/负距离向两侧偏移: 正值偏一侧, 负值偏另一侧
            (setq r1 (vl-catch-all-apply 'vla-offset (list ent-obj dist)))
            (setq r2 (vl-catch-all-apply 'vla-offset (list ent-obj (- dist))))
            (if (and (not (vl-catch-all-error-p r1))
                     (not (vl-catch-all-error-p r2)))
              (progn
                ;; 偏移成功: 取出两条新对象, 放入目标图层
                (setq o1 (vlax-safearray->list (vlax-variant-value r1))
                      o2 (vlax-safearray->list (vlax-variant-value r2)))
                (foreach new-obj (append o1 o2)
                  (vla-put-layer new-obj new-layer))
                (setq ok (1+ ok)))
              ;; 偏移失败(如圆弧半径过小等): 跳过并提示
              (progn
                (setq skip (1+ skip))
                (princ (strcat "\n  对象 #" (itoa i) " (" obj-type ") 偏移失败, 已跳过。")))))
          ;; 不支持的实体类型(文字/块/标注等): 跳过并提示
          (progn
            (setq skip (1+ skip))
            (princ (strcat "\n  对象 #" (itoa i) " (" obj-type ") 不是可偏移类型, 已跳过。"))))))
    (setq i (1+ i)))
  (princ (strcat "\n偏移完成: 成功 " (itoa ok) " 个, 跳过 " (itoa skip) " 个。"))
  (list ok skip))

;; 将指定源图层(src-layer)上所有可偏移对象向两侧各偏移 dist, 放入目标图层
(defun dt:offset-layer (src-layer new-layer dist / ss)
  (setq ss (ssget "X" (list (cons 8 src-layer))))
  (if (null ss)
    (progn
      (princ (strcat "\n图层 \"" src-layer "\" 上没有任何对象, 无需偏移。"))
      (list 0 0))
    (dt:offset-enames (dt:ss->list ss) new-layer dist)))

;; ============================================================================
;; 五、加热条专属逻辑(dt:jrt-* 前缀, 不与主脚本/出线槽脚本冲突)
;; ============================================================================

;; 图层 eName 快照(用于差集跟踪单层构建的新产物)
(defun dt:jrt-snapshot (layer / ss)
  (setq ss (ssget "X" (list (cons 8 layer))))
  (if ss (dt:ss->list ss) nil))

;; 快照之后新增的 eName 列表(= 当前图上 JRT 对象 - 快照)
(defun dt:jrt-diff (old / cur out e)
  (setq cur (dt:jrt-snapshot "JRT") out nil)
  (foreach e cur
    (if (not (member e old)) (setq out (cons e out))))
  (reverse out))

;; 曲线采样点(参数 0/0.25/0.5/0.75/1) —— 用于两条曲线最小距离估算
;; (直线=精确; 折线/弧为近似, 判定容差 1.0 足够)
(defun dt:jrt-sample-pts (obj / e out k)
  (setq e (vlax-curve-getendparam obj) out nil k 0)
  (while (<= k 4)
    (setq out (cons (vlax-curve-getpointatparam obj (* e 0.25 k)) out)
          k (1+ k)))
  (reverse out))

;; 两曲线最小距离(双向采样求最近点)
(defun dt:jrt-curve-dist (o1 o2 / d cp p)
  (setq d 1e30)
  (foreach p (dt:jrt-sample-pts o1)
    (setq cp (vl-catch-all-apply 'vlax-curve-getclosestpointto (list o2 p)))
    (if (not (vl-catch-all-error-p cp))
      (setq d (min d (distance p cp)))))
  (foreach p (dt:jrt-sample-pts o2)
    (setq cp (vl-catch-all-apply 'vlax-curve-getclosestpointto (list o1 p)))
    (if (not (vl-catch-all-error-p cp))
      (setq d (min d (distance p cp)))))
  d)

;; 两曲线是否相交或端头搭在对方身上(T接/交叉), 容差 0.5
(defun dt:jrt-touch-p (o1 o2 / hit p)
  (or (dt:inters-pts o1 o2)
      (progn
        (setq hit nil)
        (foreach p (list (vlax-curve-getstartpoint o1)
                         (vlax-curve-getendpoint o1))
          (if (< (distance p (vlax-curve-getclosestpointto o2 p)) 0.5)
            (setq hit T)))
        (foreach p (list (vlax-curve-getstartpoint o2)
                         (vlax-curve-getendpoint o2))
          (if (< (distance p (vlax-curve-getclosestpointto o1 p)) 0.5)
            (setq hit T)))
        hit)))

;; 收集 LD 曲线的自由端头(排除"端点落在其他 LD 曲线上"的交汇端)
;; 返回 ((obj 端类型"S"/"E" 端点 另一端点) ...)
(defun dt:jrt-free-ends (ld-vlas / ends obj o others et pt opt junction cp)
  (setq ends nil)
  (foreach obj ld-vlas
    (setq others nil)
    (foreach o ld-vlas
      (if (not (equal (vlax-vla-object->ename o)
                      (vlax-vla-object->ename obj)))
        (setq others (cons o others))))
    (foreach et '("S" "E")
      (setq pt (if (= et "S") (vlax-curve-getstartpoint obj)
                 (vlax-curve-getendpoint obj))
            opt (if (= et "S") (vlax-curve-getendpoint obj)
                  (vlax-curve-getstartpoint obj))
            junction nil)
      (foreach o others
        (setq cp (vl-catch-all-apply 'vlax-curve-getclosestpointto (list o pt)))
        (if (and (not (vl-catch-all-error-p cp))
                 (< (distance pt cp) 0.5))
          (setq junction T)))
      (if (not junction)
        (setq ends (cons (list obj et pt opt) ends)))))
  (reverse ends))

;; RZ 热咀圆 ↔ 自由端头匹配:
;; 圆心落在端头所在 LD 曲线近旁(垂距<0.5)且到本端点比到另一端点近 → 匹配
;; 返回 ((obj 端类型 端点 另一端点 圆心) ...), 未匹配的端头圆心为 nil
(defun dt:jrt-match-rz (free-ends rz-vlas / out rec obj et pt opt c o cp best)
  (setq out nil)
  (foreach rec free-ends
    (setq obj (nth 0 rec) et (nth 1 rec) pt (nth 2 rec) opt (nth 3 rec)
          best nil)
    (foreach o rz-vlas
      ;; 只处理圆(RZ 图层理论上只有热咀圆, 防用户手画其他实体)
      (if (= (vla-get-objectname o) "AcDbCircle")
        (progn
          (setq c (vlax-safearray->list (vlax-variant-value (vla-get-center o))))
          (setq cp (vl-catch-all-apply 'vlax-curve-getclosestpointto (list obj c)))
          (if (and (not (vl-catch-all-error-p cp))
                   (< (distance c cp) 0.5)
                   (< (distance c pt) (distance c opt)))
            ;; 多个候选时取离端点最近者
            (if (or (null best) (< (distance c pt) (distance (nth 4 best) pt)))
              (setq best (list obj et pt opt c)))))))
    (if best
      (setq out (cons best out))
      (setq out (cons (list obj et pt opt nil) out))))
  (reverse out))

;; 端头帽形式判定(全部端头在此统一判定一次, 三层共用):
;; gap = 端头所在 LD 曲线与其他"不相交/T接"LD 曲线的最小轴线距 - 2×偏移值
;;   |gap - 偏移值| <= 1.0 且有匹配 RZ → "circle"(RZ 处整圆帽)
;;   gap > 偏移值 或 无相邻/无 RZ       → "line"(直线帽)
;;   gap < 偏移值 - 1.0                 → 告警 + "line"
;; 返回 ((obj 端类型 端点 另一端点 圆心 形式 gap 内向方向) ...)
(defun dt:jrt-decide (ld-vlas matched / plans rec obj et pt opt c inward gap d style
                      e-obj o)
  (setq plans nil)
  (foreach rec matched
    (setq obj (nth 0 rec) et (nth 1 rec) pt (nth 2 rec)
          opt (nth 3 rec) c (nth 4 rec))
    ;; 内向方向: 有 RZ 用"端点→圆心", 无 RZ 用"端点→另一端点"(指向通道内部)
    (setq inward (if c (dt:unit (mapcar '- c pt)) (dt:unit (mapcar '- opt pt))))
    ;; 相邻通道内壁间距
    (setq gap nil e-obj (vlax-vla-object->ename obj))
    (foreach o ld-vlas
      (if (not (equal (vlax-vla-object->ename o) e-obj))
        (if (not (dt:jrt-touch-p obj o))
          (setq d (dt:jrt-curve-dist obj o)
                gap (if gap (min gap d) d)))))
    (if gap (setq gap (- gap (* 2.0 *jrt-offset*))))
    ;; 判定
    (setq style "line")
    (cond
      ((and c gap (< (abs (- gap *jrt-offset*)) 1.0))
       (setq style "circle"))
      ((and c gap (< gap (- *jrt-offset* 1.0)))
       (princ (strcat "\n【端帽】警告: 端头(" (rtos (car pt) 2 1) "," (rtos (cadr pt) 2 1)
                      ") 相邻通道内壁间距 " (rtos gap 2 2) " 过近, 改用直线帽。")))
      ((and c gap)
       ;; gap > 偏移值: 正常直线帽
       )
      ((and c (null gap))
       (princ (strcat "\n【端帽】提示: 端头(" (rtos (car pt) 2 1) "," (rtos (cadr pt) 2 1)
                      ") 无相邻通道, 使用直线帽。")))
      (t
       (princ (strcat "\n【端帽】警告: 端头(" (rtos (car pt) 2 1) "," (rtos (cadr pt) 2 1)
                      ") 未匹配到 RZ 热咀圆, 使用直线帽。"))))
    (princ (strcat "\n【端帽】端头(" (rtos (car pt) 2 1) "," (rtos (cadr pt) 2 1) "): "
                   (if gap (strcat "相邻通道内壁间距 " (rtos gap 2 2)) "无相邻通道")
                   " → " (if (= style "circle") "RZ处整圆帽" "直线帽") "。"))
    (setq plans (cons (list obj et pt opt c style gap inward) plans)))
  (reverse plans))

;; 找端头的两条侧壁线(本层实体中, 端头点距 LD 端点≈半宽的线端)
;; 返回 ((obj 端类型 端头点) ...)
(defun dt:jrt-head-walls (ents pt hw / walls e obj sp ep)
  (setq walls nil)
  (foreach e ents
    (setq obj (vlax-ename->vla-object e))
    (if (= (vla-get-objectname obj) "AcDbLine")
      (progn
        (setq sp (vlax-curve-getstartpoint obj)
              ep (vlax-curve-getendpoint obj))
        (if (< (abs (- (distance sp pt) hw)) 0.6)
          (setq walls (cons (list obj "S" sp) walls)))
        (if (< (abs (- (distance ep pt) hw)) 0.6)
          (setq walls (cons (list obj "E" ep) walls))))))
  walls)

;; 圆帽: 在 RZ 圆心处画整圆 R=半宽(与两测线相切), 侧线端头修到切点
;; plan = (obj et pt opt c style gap inward)
(defun dt:jrt-cap-circle (plan ents hw / et pt c inward nrm walls wall wallpt
                          sign tang len ms new-c cnt)
  (setq et (nth 1 plan) pt (nth 2 plan)
        c (nth 4 plan) inward (nth 7 plan)
        nrm (list (- (cadr inward)) (car inward) 0.0)
        walls (dt:jrt-head-walls ents pt hw)
        cnt 0)
  (foreach wall walls
    (setq wallpt (nth 2 wall)
          sign (if (>= (apply '+ (mapcar '* (mapcar '- wallpt pt) nrm)) 0.0) 1.0 -1.0)
          tang (dt:pt+vec c nrm (* sign hw))
          len (vlax-curve-getdistatparam (car wall)
                (vlax-curve-getendparam (car wall))))
    ;; 切点必须在侧线当前长度内(侧线另一端要长于轴向距离)
    (if (> len (+ (distance pt c) 1.0))
      (progn (dt:set-endpoint (car wall) (cadr wall) tang) (setq cnt (1+ cnt)))
      (princ "\n【端帽】警告: 侧壁过短, 圆帽切点超出侧线, 该侧线未修剪。")))
  (setq ms (dt:ms)
        new-c (vla-addcircle ms (vlax-3d-point c) hw))
  (vla-put-layer new-c "JRT")
  cnt)

;; 直线帽(v9.6 重构): 封闭线与两条相接的偏移线圆弧衔接 ——
;;   - 封闭线圆角半径R >= 半宽(默认 29=29): 封闭线直接替换为一个圆弧:
;;     圆心 = 帽线中点沿通道向内偏半宽, 半径 = 半宽, 与两测线相切,
;;     半圆凸向端点平面, 侧线端头修到切点;
;;   - 封闭线圆角半径R < 半宽: 端点平面向内偏 inset 画直线封闭线,
;;     两端与测线解析法圆角(半径 = 封闭线圆角半径R), 侧线端头修到切点,
;;     裁掉端点平面方向多余段。
;; plan = (obj et pt opt c style gap inward)
(defun dt:jrt-cap-line (plan ents hw inset capr / et pt inward nrm walls wall
                        wallpt sign target cap-mid center tan1 tan2 p1 p2 ucap q1
                        q2 s1 s2 o1 o2 a1 a2 am ms ln arc sw rel tmp sq2 cnt pair)
  (setq et (nth 1 plan) pt (nth 2 plan)
        inward (nth 7 plan)
        nrm (list (- (cadr inward)) (car inward) 0.0)
        walls (dt:jrt-head-walls ents pt hw)
        cnt 0
        ms (dt:ms))
  (if (>= capr (- hw 0.01))
    ;; ===== 圆弧替换模式: 封闭线 = 一个与两测线相切的圆弧 =====
    (progn
      (setq cap-mid (dt:pt+vec pt inward inset)
            center  (dt:pt+vec cap-mid inward hw))
      (foreach wall walls
        (setq wallpt (nth 2 wall)
              sign (if (>= (apply '+ (mapcar '* (mapcar '- wallpt pt) nrm)) 0.0)
                     1.0 -1.0)
              target (dt:pt+vec center nrm (* sign hw)))
        (dt:set-endpoint (car wall) (cadr wall) target)
        (setq cnt (1+ cnt)))
      ;; 半圆弧: 两切点之间经过帽线中点(凸向端点平面)
      (setq tan1 (dt:pt+vec center nrm (- hw))
            tan2 (dt:pt+vec center nrm hw)
            a1 (angle (list (car center) (cadr center))
                      (list (car tan1) (cadr tan1)))
            a2 (angle (list (car center) (cadr center))
                      (list (car tan2) (cadr tan2)))
            am (angle (list (car center) (cadr center))
                      (list (car cap-mid) (cadr cap-mid)))
            sw (if (> a2 a1) (- a2 a1) (+ (- a2 a1) (* 2 pi)))
            rel (if (> am a1) (- am a1) (+ (- am a1) (* 2 pi))))
      (if (>= rel sw)
        (setq tmp a1 a1 a2 a2 tmp))
      (setq arc (vla-addarc ms (vlax-3d-point center) hw a1 a2))
      (vla-put-layer arc "JRT"))
    ;; ===== 直线 + 两端圆角模式 =====
    (progn
      (setq p1 (dt:pt+vec (dt:pt+vec pt inward inset) nrm (- hw))
            p2 (dt:pt+vec (dt:pt+vec pt inward inset) nrm hw)
            ucap (dt:unit (mapcar '- p2 p1)))
      ;; 侧线端头从端点平面修到圆角切点(角点沿通道向内 capr)
      (foreach wall walls
        (setq wallpt (nth 2 wall)
              sign (if (>= (apply '+ (mapcar '* (mapcar '- wallpt pt) nrm)) 0.0)
                     1.0 -1.0)
              target (dt:pt+vec (dt:pt+vec (dt:pt+vec pt inward inset)
                                           nrm (* sign hw))
                                inward capr))
        (dt:set-endpoint (car wall) (cadr wall) target)
        (setq cnt (1+ cnt)))
      (if (< capr 0.01)
        ;; 半径≈0: 直角直接相接
        (progn
          (setq ln (vla-addline ms (vlax-3d-point p1) (vlax-3d-point p2)))
          (vla-put-layer ln "JRT"))
        (progn
          (setq sq2 (* capr (sqrt 2.0))
                q1 (dt:pt+vec p1 ucap capr)
                q2 (dt:pt+vec p2 (mapcar '- ucap) capr)
                s1 (dt:pt+vec p1 inward capr)
                s2 (dt:pt+vec p2 inward capr)
                o1 (dt:pt+vec p1 (dt:unit (mapcar '+ ucap inward)) sq2)
                o2 (dt:pt+vec p2 (dt:unit (mapcar '- ucap inward)) sq2))
          ;; 直线封闭线只画到两切点之间
          (setq ln (vla-addline ms (vlax-3d-point q1) (vlax-3d-point q2)))
          (vla-put-layer ln "JRT")
          ;; 两端 90° 圆角弧(劣弧)
          (foreach pair (list (list o1 q1 s1) (list o2 q2 s2))
            (setq a1 (angle (list (car (car pair)) (cadr (car pair)))
                            (list (car (cadr pair)) (cadr (cadr pair))))
                  a2 (angle (list (car (car pair)) (cadr (car pair)))
                            (list (car (caddr pair)) (cadr (caddr pair)))))
            (if (> (if (> a2 a1) (- a2 a1) (+ (- a2 a1) (* 2 pi))) pi)
              (setq tmp a1 a1 a2 a2 tmp))
            (setq arc (vla-addarc ms (vlax-3d-point (car pair)) capr a1 a2))
            (vla-put-layer arc "JRT"))))))
  (if (< cnt 2)
    (princ (strcat "\n【端帽】警告: 端头(" (rtos (car pt) 2 1) "," (rtos (cadr pt) 2 1)
                   ") 只找到 " (itoa cnt) " 条侧壁, 帽线可能悬空。")))
  cnt)

;; 区域裁剪(dt:jrt-trim): 对本层实体做 LD ±hw 带状裁剪(逻辑同主脚本 trim-all,
;; 但对象限定在传入的 eName 列表, 三层互不干扰)
(defun dt:jrt-trim (ents hw / ld vla-list pts-pairs pair trim-count skip-count)
  (setq ld (dt:curves-only (dt:layer-vlas "LD")))
  (if (null ld)
    (princ "\n【裁剪】未找到\"LD\"图层, 无法确定流道区域, 跳过裁剪。")
    (progn
      (setq vla-list (mapcar 'vlax-ename->vla-object ents))
      (if (null vla-list)
        (princ "\n【裁剪】本层没有对象, 无需裁剪。")
        (progn
          (setq pts-pairs (dt:cross-points vla-list))
          (dt:jrt-undo-mark)
          (setq trim-count 0 skip-count 0)
          (foreach pair pts-pairs
            (if (dt:jrt-trim-curve (car pair) (cdr pair) ld hw "JRT")
              (setq trim-count (1+ trim-count))
              (setq skip-count (1+ skip-count))))
          (dt:jrt-undo-end)
          (princ (strcat "\n【裁剪】完成: 处理 " (itoa trim-count)
                         " 条线, 跳过 " (itoa skip-count) " 条。"))))))
  (princ))

;; 统一断口圆角(dt:jrt-fillet): 交汇断口与直线帽直角交汇一并处理
;; (端头重合配对后逐个圆角, r-start=本层圆角半径)
(defun dt:jrt-fillet (ents hw r / ld e obj-type vla-list heads pairs pair res
                      count-ok count-fail count-dec)
  (setq ld (dt:curves-only (dt:layer-vlas "LD")))
  (if (null ld)
    (princ "\n【圆角】未找到\"LD\"图层, 无法验证圆角方向, 跳过圆角处理。")
    (progn
      ;; 只对直线/弧/多段线收集端头(排除帽圆)
      (setq vla-list nil)
      (foreach e ents
        (setq obj-type (vla-get-objectname (vlax-ename->vla-object e)))
        (if (member obj-type '("AcDbLine" "AcDbArc"
                               "AcDbLWPolyline" "AcDbPolyline"))
          (setq vla-list (cons (vlax-ename->vla-object e) vla-list))))
      (setq vla-list (reverse vla-list))
      (if (null vla-list)
        (princ "\n【圆角】本层没有可圆角的线。")
        (progn
          (setq heads (dt:collect-heads vla-list nil)
                pairs (dt:pair-heads heads))
          (dt:jrt-undo-mark)
          (setq count-ok 0 count-fail 0 count-dec 0)
          (foreach pair pairs
            (setq res (dt:jrt-fillet-pair (car pair) (cadr pair) ld hw "JRT" r))
            (if res
              (progn
                (setq count-ok (1+ count-ok))
                (if (< (car res) r) (setq count-dec (1+ count-dec))))
              (setq count-fail (1+ count-fail))))
          (dt:jrt-undo-end)
          (princ (strcat "\n【圆角】发现 " (itoa (length pairs)) " 处断口: 成功 "
                         (itoa count-ok) " 处, 失败 " (itoa count-fail) " 处"
                         (if (> count-dec 0)
                           (strcat " (其中 " (itoa count-dec) " 处半径递减, 已标注)")
                           "")
                         "。"))))))
  (princ))

;; 零长线清理: 圆角恰好消化整条帽线时, 帽线两端切点重合留下零长残段
(defun dt:jrt-zero-clean (ents / e obj sp ep)
  (foreach e ents
    (setq obj (vl-catch-all-apply 'vlax-ename->vla-object (list e)))
    (if (not (vl-catch-all-error-p obj))
      (progn
        (if (= (vl-catch-all-apply 'vla-get-objectname (list obj)) "AcDbLine")
          (progn
            (setq sp (vl-catch-all-apply 'vla-get-startpoint (list obj))
                  ep (vl-catch-all-apply 'vla-get-endpoint (list obj)))
            (if (and (listp sp) (listp ep)
                     (< (distance sp ep) 1e-6))
              (vl-catch-all-apply 'vla-delete (list obj))))))))
  (princ))

;; 取当前模板行(下标越界回退第 1 个)
(defun dt:jrt-template-row ( / row)
  (setq row (nth *jrt-template* dt:jrt-template-table))
  (if row row (nth 0 dt:jrt-template-table)))

;; 环节覆盖分发(v9.8): 查当前模板覆盖表, 有覆盖则调覆盖函数, 否则调默认函数
;; stage = 'decide / 'cap-circle / 'cap-line / 'build
;; ('process 为 v9.9 新增的主流程环节, 不经本分发 —— 由 c:JRT 直接调用)
(defun dt:jrt-stage (stage default-fn args / ov)
  (setq ov (assoc stage (nth 3 (dt:jrt-template-row))))
  (apply (if ov (cdr ov) default-fn) args))

;; 单层构建: 偏移 → 裁剪 → 端帽 → 断口圆角 → 零长清理
;; plans 来自 decide 环节(各层共用同一端帽形式)
;; 返回 (圆帽数 直线帽数)
(defun dt:jrt-build (hw inset r capr plans / snap ents plan cnt-circle cnt-line)
  (setq snap (dt:jrt-snapshot "JRT"))
  ;; 1) 偏移 LD → JRT(半宽 hw)
  (dt:offset-layer "LD" "JRT" hw)
  (setq ents (dt:jrt-diff snap))
  ;; 2) 交汇区域裁剪(裁剪会删除重建对象 → 差集刷新实体列表)
  (dt:jrt-trim ents hw)
  (setq ents (dt:jrt-diff snap))
  ;; 3) 端帽(圆帽/直线帽, 按 decide 环节的判定; 先建帽线/帽圆再修侧壁端头)
  (dt:jrt-undo-mark)
  (setq cnt-circle 0 cnt-line 0)
  (foreach plan plans
    (if (= (nth 5 plan) "circle")
      (progn (dt:jrt-stage 'cap-circle 'dt:jrt-cap-circle (list plan ents hw))
             (setq cnt-circle (1+ cnt-circle)))
      (progn (dt:jrt-stage 'cap-line 'dt:jrt-cap-line (list plan ents hw inset capr))
             (setq cnt-line (1+ cnt-line)))))
  (dt:jrt-undo-end)
  ;; 4) 统一断口圆角(交汇断口 + 直线帽两端直角交汇)
  (setq ents (dt:jrt-diff snap))
  (dt:jrt-fillet ents hw r)
  ;; 5) 零长残段清理
  (dt:jrt-zero-clean (dt:jrt-diff snap))
  (princ (strcat "\n【加热条】半宽 " (rtos hw 2 1) " 层完成: 圆帽 "
                 (itoa cnt-circle) " 处, 直线帽 " (itoa cnt-line) " 处。"))
  (list cnt-circle cnt-line))

;; ============================================================================
;; 五.5、两点式模板(dt:jrt2-*, v9.9) —— 源线="JRT"图层曲线, 第 k 层把每段
;;      源线朝 "JRTDW"(加热条定位)实体方向偏 k×步长; 出线的每个"头"用一条
;;      直线把最外侧与最内侧端头连起来(中间层端头由线跨过)成闭环;
;;      无裁剪/端帽/圆角; 源线保留, 上一轮产物按句柄记忆重跑先删。
;; ============================================================================

;; obj 与组内任一曲线端点相接(<tol)?
(defun dt:jrt2-grp-touch (obj g tol / r p1 p2 o2)
  (setq p1 (vlax-curve-getstartpoint obj)
        p2 (vlax-curve-getendpoint obj)
        r nil)
  (foreach o2 g
    (if (not r)
      (if (or (< (distance p1 (vlax-curve-getstartpoint o2)) tol)
              (< (distance p1 (vlax-curve-getendpoint o2)) tol)
              (< (distance p2 (vlax-curve-getstartpoint o2)) tol)
              (< (distance p2 (vlax-curve-getendpoint o2)) tol))
        (setq r T))))
  r)

;; 源线按端点相接(<tol)并组成"条"(连通分量); 返回 (vla列表 ...) 的列表
(defun dt:jrt2-group (srcs tol / groups g hit1 hit2 obj)
  (foreach obj srcs
    (setq hit1 nil hit2 nil)
    (foreach g groups
      (if (dt:jrt2-grp-touch obj g tol)
        (if (null hit1) (setq hit1 g) (setq hit2 g))))
    (cond
      ((null hit1) (setq groups (cons (list obj) groups)))
      ((null hit2) (setq groups (cons (append hit1 (list obj))
                                      (vl-remove hit1 groups))))
      (T (setq groups (cons (append hit1 hit2 (list obj))
                            (vl-remove hit2 (vl-remove hit1 groups)))))))
  groups)

;; 单段源线 ±dist 各试偏一次, 返回成功创建的候选 vla 列表(0~2 个, 已置
;; layer 层; 选边由 dt:jrt2-layer 传播完成, 本函数不做方向判断)
;; v9.25: 创建即登记句柄到 *jrt2-made* —— 任何中途出错留下的落选废候选,
;; 下次运行步骤 2 都能按句柄自动清走(旧版只在结束时登记, 崩溃即失控)
(defun dt:jrt2-cands (obj dist layer / r lst v sgn)
  (setq lst nil)
  (foreach sgn (list dist (- dist))
    (setq r (vl-catch-all-apply 'vla-offset (list obj sgn)))
    (if (not (vl-catch-all-error-p r))
      (progn
        (setq v (car (vlax-safearray->list (vlax-variant-value r))))
        (vla-put-layer v layer)
        (vl-catch-all-apply
          '(lambda ( / h)
             (setq h (vla-get-handle v))
             (if (and h (stringp h)) (setq *jrt2-made* (cons h *jrt2-made*)))))
        (setq lst (cons v lst)))))
  lst)

;; 曲线 3 个采样点到实体集(dw-vlas)的最小距离;
;; 采样点/最近点计算全部捕获异常 —— dw-vlas 里混入文字等无曲线实体时
;; getclosestpointto 会返回 nil, 跳过该实体而非崩掉(坑: 二维/三维点 nil)
(defun dt:jrt2-min-dist (obj dw-vlas / fr m cp d best dw)
  (setq best 1e99)
  (foreach fr '(0.25 0.5 0.75)
    (setq m (vl-catch-all-apply 'vlax-curve-getpointatparam
              (list obj (* (vlax-curve-getendparam obj) fr))))
    (if (not (vl-catch-all-error-p m))
      (foreach dw dw-vlas
        (setq cp (vl-catch-all-apply 'vlax-curve-getclosestpointto
                   (list dw m)))
        (if (not (vl-catch-all-error-p cp))
          (progn
            (setq d (distance m cp))
            (if (< d best) (setq best d)))))))
  best)

;; 候选列表中取离 JRTDW 最近者
(defun dt:jrt2-pick-near (cands dw-vlas / best bd c d)
  (setq best nil bd 1e99)
  (foreach c cands
    (setq d (dt:jrt2-min-dist c dw-vlas))
    (if (< d bd) (setq bd d best c)))
  best)

;; ============================================================================
;; v9.24 几何内外判定 —— "内" = 轮廓条围合闭合区域的内部(奇偶射线规则),
;; 不再依赖 JRTDW 画向; JRTDW 只作歧义兜底(见 dt:jrt2-pick-side)。
;; ============================================================================

;; 曲线采样成连续边段 ((pa pb) ...); n=分段数(直线精确, 弧/多段线近似)
;; v9.25: vlax-curve 系列越界时会"返回 nil 而不抛错"(实证范本 wx_runner
;; dt:sz-curve-sample-pts), 光判 vl-catch-all-error-p 会让 nil 点混进边集,
;; 下游 (min (cadr a) (cadr b)) 即炸 "参数类型错误: numberp: nil" —— 全部
;; 双判 (error-p)+非nil
(defun dt:jrt2-curve-edges (obj n / ep k prev p out)
  (setq ep (vl-catch-all-apply 'vlax-curve-getendparam (list obj)))
  (cond
    ((or (vl-catch-all-error-p ep) (not (numberp ep))) nil)
    (T
     (setq out nil prev nil k 0)
     (while (<= k n)
       (setq p (vl-catch-all-apply 'vlax-curve-getpointatparam
                   (list obj (* ep (/ (float k) (float n))))))
       (if (or (vl-catch-all-error-p p) (null p))
         nil
         (progn
           (if prev (setq out (cons (list prev p) out)))
           (setq prev p)))
       (setq k (1+ k)))
     out)))

;; 轮廓条(指定采样段数)→ 闭合区域边集: 各段采样边 + 自由端头贪心最近配对
;; 封口(出线口打开处/未合拢处按最短距离两两连线, 与 dt:jrt2-close 的配对
;; 思路一致)。v9.26: n 可调 —— 大半径弧在 n=12 时弦割线内缩可达 13.6mm,
;; 会吞掉 5mm 探针致奇偶漏判; 颈线方向判定用 n=24(R≤400 误差 ≈3.4mm)
(defun dt:jrt2-region-edges-n (bar n / obj edges ends s1 s2 d best)
  (setq edges nil)
  (foreach obj bar
    (setq edges (append (dt:jrt2-curve-edges obj n) edges)))
  (setq ends (mapcar 'car (dt:jrt2-free-ends bar 0.5)))
  (while (> (length ends) 1)
    (setq s1 (car ends) best nil d 1e99)
    (foreach s2 (cdr ends)
      (if (< (distance s1 s2) d) (setq d (distance s1 s2) best s2)))
    (setq edges (cons (list s1 best) edges)
          ends (vl-remove s1 (vl-remove best ends))))
  edges)

;; 默认 12 段采样版(嵌套内偏围合判定用; 颈线方向判定用 -n 24)
(defun dt:jrt2-region-edges (bar / )
  (dt:jrt2-region-edges-n bar 12))

;; 点在围合区域内?(+X 射线交点计数, 奇=内; edges=nil → 不可判定返回 nil)
;; v9.25: 防御性跳过含非点端点的边(理论上 curve-edges 已滤净, 双保险)
(defun dt:jrt2-pt-inside (pt edges / x y cnt e a b ix)
  (cond
    ((null edges) nil)
    ((or (null pt) (null (car pt)) (null (cadr pt))) nil)
    (T
     (setq x (car pt) y (cadr pt) cnt 0)
     (foreach e edges
       (setq a (car e) b (cadr e))
       (if (and (listp a) (listp b) (numberp (cadr a)) (numberp (cadr b))
                (< (min (cadr a) (cadr b)) y)
                (>= (max (cadr a) (cadr b)) y))
         (progn
           (setq ix (+ (car a) (/ (* (- y (cadr a)) (- (car b) (car a)))
                                  (- (cadr b) (cadr a)))))
           (if (> ix x) (setq cnt (1+ cnt))))))
     (= 1 (rem cnt 2)))))

;; 曲线中点(失败返回 nil; v9.25 nil 双判)
(defun dt:jrt2-mid-pt (obj / ep p)
  (setq ep (vl-catch-all-apply 'vlax-curve-getendparam (list obj)))
  (cond
    ((or (vl-catch-all-error-p ep) (not (numberp ep))) nil)
    (T
     (setq p (vl-catch-all-apply 'vlax-curve-getpointatparam (list obj (* ep 0.5))))
     (if (or (vl-catch-all-error-p p) (null p)) nil p))))

;; 曲线长度(失败返回 0.0; v9.25: getdistatparam 也可能返回 nil 而非抛错)
(defun dt:jrt2-curve-len (obj / e d)
  (setq e (vl-catch-all-apply 'vlax-curve-getendparam (list obj)))
  (cond
    ((or (vl-catch-all-error-p e) (not (numberp e))) 0.0)
    (T
     (setq d (vl-catch-all-apply 'vlax-curve-getdistatparam (list obj e)))
     (if (or (vl-catch-all-error-p d) (not (numberp d))) 0.0 d))))

;; 候选选边(v9.24, v9.25 起仅作 FLB 判据不可用时的回退): 中点落在轮廓围合区域
;; 内的"唯一"候选 = 内侧; 0 个或多个(歧义) → 再回退"离 JRTDW 近"规则
(defun dt:jrt2-pick-side (cands edges dw-vlas / c m ins)
  (setq ins nil)
  (foreach c cands
    (setq m (dt:jrt2-mid-pt c))
    (if (and m (dt:jrt2-pt-inside m edges))
      (setq ins (cons c ins))))
  (if (= 1 (length ins))
    (car ins)
    (dt:jrt2-pick-near cands dw-vlas)))

;; 曲线 5 个等距采样点(弧长参数; 零长曲线退化为起点; 全失败 nil)
(defun dt:jrt2-samples (obj / L p fr out)
  (setq L (dt:jrt2-curve-len obj) out nil)
  (if (> L 0.0)
    (foreach fr (list 0.1 0.3 0.5 0.7 0.9)
      (setq p (vl-catch-all-apply 'vlax-curve-getpointatdist
                  (list obj (* L fr))))
      (if (and (not (vl-catch-all-error-p p)) p) (setq out (cons p out))))
    (progn
      (setq p (vl-catch-all-apply 'vlax-curve-getstartpoint (list obj)))
      (if (and (not (vl-catch-all-error-p p)) p) (setq out (list p)))))
  out)

;; 单点到曲线组最小距离(全失败 nil)
(defun dt:jrt2-pt-curves-dist (pt curves / cp d o best)
  (setq best nil)
  (foreach o curves
    (setq cp (vl-catch-all-apply 'vlax-curve-getclosestpointto (list o pt)))
    (if (and (not (vl-catch-all-error-p cp)) cp)
      (progn
        (setq d (distance pt cp))
        (if (or (null best) (< d best)) (setq best d)))))
  best)

;; 曲线集整体 FLB 亲近度(v9.25 主判据核心): 每条曲线取"采样点到 FLB 的
;; 最小距离", 再对曲线求均值。数值越大 = 离 FLB 壁越远 = 越朝板内。
;; 曲线集空 / FLB 空 / 一切测距失败 → nil(不可判定)
(defun dt:jrt2-flb-score (curves flb-vlas / o omin m d sum cnt)
  (cond
    ((or (null curves) (null flb-vlas)) nil)
    (T
     (setq sum 0.0 cnt 0)
     (foreach o curves
       (setq omin nil)
       (foreach m (dt:jrt2-samples o)
         (setq d (dt:jrt2-pt-curves-dist m flb-vlas))
         (if (and d (or (null omin) (< d omin))) (setq omin d)))
       (if omin (setq sum (+ sum omin) cnt (1+ cnt))))
     (if (> cnt 0) (/ sum cnt) nil))))

;; 从指定锚段指定候选出发, 沿端点相接链整环传播选边(v9.25 非破坏式:
;; 只算选中表不删任何东西, 以便 A/B 两个种子各跑一遍后比较取舍)。
;; recs=((obj 候选 已选)...); 返回 ((obj . 选中候选) ...) 选中表
(defun dt:jrt2-propagate (recs seed-obj seed-cand / out queue curobj ch
                              e-s e-e ref-pt pt obj2 rec2 s2 e2 cnb dnb c d)
  (setq out (list (cons seed-obj seed-cand))
        queue (list seed-obj))
  (while queue
    (setq curobj (car queue)
          queue (cdr queue)
          ch (cdr (assoc curobj out)))
    (if ch
      (foreach pt (list (vlax-curve-getstartpoint curobj)
                        (vlax-curve-getendpoint curobj))
        ;; 已选候选在本端点侧的端头 = 传播参考点
        (setq e-s (vlax-curve-getstartpoint ch)
              e-e (vlax-curve-getendpoint ch)
              ref-pt (if (< (distance pt e-s) (distance pt e-e)) e-s e-e))
        (foreach obj2 (mapcar 'car recs)
          (setq rec2 (assoc obj2 recs))
          (if (and (not (assoc obj2 out))
                   (not (equal obj2 curobj)))
            (progn
              (setq s2 (vlax-curve-getstartpoint obj2)
                    e2 (vlax-curve-getendpoint obj2))
              (if (or (< (distance s2 pt) 0.5) (< (distance e2 pt) 0.5))
                (progn
                  ;; 取其候选端头离参考点最近者(切线接头处同侧端点重合距离0)
                  (setq cnb nil dnb 1e99)
                  (foreach c (nth 1 rec2)
                    (setq e-s (vlax-curve-getstartpoint c)
                          e-e (vlax-curve-getendpoint c)
                          d (min (distance ref-pt e-s)
                                 (distance ref-pt e-e)))
                    (if (< d dnb) (setq dnb d cnb c)))
                  (if cnb
                    (progn
                      (setq out (cons (cons obj2 cnb) out)
                            queue (append queue (list obj2)))))))))))))
  out)

;; 一条源线的单层内偏选边(v9.25, 用户定案规则):
;;   ① 每段 ±dist 双候选先全部建出(不先删);
;;   ② 锚段=条内最长段, 其两个候选各作种子做整环链传播 → RingA/RingB;
;;   ③ 主判据=离 FLB 壁距离: 两环各求 dt:jrt2-flb-score, 得分更大者
;;     (离 FLB 更远) = 朝内 —— "偏移之后距 FLB 更近说明方向反了";
;;     FLB 缺失或得分不可比 → 回退 v9.24 围合区域奇偶判定; 再不可 → v9.9
;;     "离 JRTDW 近"兜底;
;;   ④ 传播未及的孤立段按同一判据链单独裁决;
;;   ⑤ 最后一次性删除全部落选候选(判定阶段零删除, 中途出错不留半圈废线;
;;     候选创建即记句柄, 崩溃残留也会被下次运行步骤 2 清走)。
;; 返回选中 vla 列表(已置于 layer 层)
(defun dt:jrt2-layer (bar dist layer dw-vlas flb-vlas / recs anchor ad d
                          sA sB ringA ringB edges edges-done out obj c rec
                          cand found sc)
  ;; ① 候选(±dist)
  (setq recs nil)
  (foreach obj bar
    (setq recs (cons (list obj (dt:jrt2-cands obj dist layer) nil) recs)))
  ;; ② 锚段 = 最长段
  (setq anchor nil ad -1.0)
  (foreach rec recs
    (setq d (dt:jrt2-curve-len (car rec)))
    (if (> d ad) (setq ad d anchor rec)))
  ;; ③ 整环裁决(胜者统一放在 ringA; ringB 仅中间量)
  (setq ringA nil ringB nil sA nil sB nil)
  (cond
    ((null anchor) nil)
    ((>= (length (nth 1 anchor)) 2)
     (setq ringA (dt:jrt2-propagate recs (car anchor) (car (nth 1 anchor)))
           ringB (dt:jrt2-propagate recs (car anchor) (cadr (nth 1 anchor)))
           sA (dt:jrt2-flb-score (mapcar 'cdr ringA) flb-vlas)
           sB (dt:jrt2-flb-score (mapcar 'cdr ringB) flb-vlas))
     (cond
       ;; 主判据: 两环 FLB 距离得分可比 → 更大者(离 FLB 更远=朝内)胜
       ((and sA sB)
        (if (< sA sB) (setq ringA ringB)))
       ;; 回退 1: 围合区域奇偶判定锚段选边 → 单环传播
       (T
        (setq edges-done T
              edges (dt:jrt2-region-edges bar)
              ringA (dt:jrt2-propagate recs (car anchor)
                                       (dt:jrt2-pick-side (nth 1 anchor) edges dw-vlas))))))
    ;; 锚段仅 1 候选(另一侧偏移失败): 直接作种子
    ((car (nth 1 anchor))
     (setq ringA (dt:jrt2-propagate recs (car anchor) (car (nth 1 anchor)))))
    ;; 锚段无候选(极端): 不传播, 全部段走孤立裁决
    (T (setq ringA nil)))
  (setq out ringA)
  (foreach rec recs
    (setq obj (car rec)
          cand (cdr (assoc obj out)))
    (if (null cand)
      (progn
        (setq found nil)
        ;; 判据链: FLB 距离 → 围合区域 → JRTDW 就近
        (if flb-vlas
          (progn
            (setq sc nil)
            (foreach c (nth 1 rec)
              (setq d (dt:jrt2-flb-score (list c) flb-vlas))
              (if (and d (or (null sc) (> d (cdr sc)))) (setq sc (cons c d))))
            (if sc (setq found (car sc)))))
        (if (null found)
          (progn
            (if (null edges-done)
              (progn (setq edges-done T
                           edges (dt:jrt2-region-edges bar))))
            (setq found (dt:jrt2-pick-side (nth 1 rec) edges dw-vlas))))
        (if found (setq out (cons (cons obj found) out))))))
  ;; ⑤ 收集选中 + 一次性删除落选候选
  (setq found nil)
  (foreach rec recs
    (setq cand (cdr (assoc (car rec) out)))
    (if cand
      (setq found (cons cand found))
      (princ "\n【警告】两点式: 该段源线偏移失败, 已跳过。"))
    (foreach c (nth 1 rec)
      (if (not (equal c cand))
        (vl-catch-all-apply 'vla-delete (list c)))))
  found)

;; 收集曲线列表的自由端头: 端点在 tol 内无其他曲线端点与之重合(切线接头
;; 端点重合, 不计); 闭合曲线(首尾端点重合)不计端头。
;; 返回 ends 格式: (端点坐标 对象 "S"/"E") —— 端点格式勿混用(坑#31)
(defun dt:jrt2-free-ends (curves tol / pts out rec obj pt et ok o2)
  (setq pts nil)
  (foreach obj curves
    (if (>= (distance (vlax-curve-getstartpoint obj)
                      (vlax-curve-getendpoint obj)) tol)
      (foreach et '("S" "E")
        (setq pts (cons (list (if (= et "S")
                                (vlax-curve-getstartpoint obj)
                                (vlax-curve-getendpoint obj))
                              obj et)
                        pts)))))
  (setq out nil)
  (foreach rec pts
    (setq pt (car rec) ok T)
    (foreach o2 pts
      (if (and (not (equal (cadr o2) (cadr rec)))
               (< (distance pt (car o2)) tol))
        (setq ok nil)))
    (if ok (setq out (cons rec out))))
  out)

;; 破口封闭(v9.9 规则: 出线的每个"头"一条线): 源线(最外侧, k=0)的每个
;; 自由端头, 与最近的"最内层"(k=最大层号)自由端头连一条直线 —— 中间层
;; 端头由该线跨过, 不管一头有多少破口都只此一条; 贪心最近配对保证两头
;; 各连各的。ends=(端点 对象 端类型), kmap=((对象 . 层号k)); 返回新建封闭线
(defun dt:jrt2-close (ends kmap layer / rec e r k kmax srcs inns
                          s i d dd s1 i1 pairs p ln out)
  (setq rec nil)
  (foreach e ends
    (setq k (cdr (assoc (cadr e) kmap)))
    (setq rec (cons (list (car e) k) rec)))
  (setq kmax 0)
  (foreach r rec
    (if (> (cadr r) kmax) (setq kmax (cadr r))))
  (if (< kmax 1)
    (progn
      (princ "\n【通用二】无内向偏移层, 跳过破口封闭。")
      nil)
    (progn
      (setq srcs nil inns nil)
      (foreach r rec
        (cond ((= (cadr r) 0) (setq srcs (cons (car r) srcs)))
              ((= (cadr r) kmax) (setq inns (cons (car r) inns)))))
      ;; 贪心最近配对: 最外侧端头 ↔ 最内侧端头
      (setq pairs nil)
      (while (and srcs inns)
        (setq s nil i nil d 1e99)
        (foreach s1 srcs
          (foreach i1 inns
            (setq dd (distance s1 i1))
            (if (< dd d)
              (setq d dd s s1 i i1))))
        (if s
          (progn
            (setq pairs (cons (list s i) pairs)
                  srcs (vl-remove s srcs)
                  inns (vl-remove i inns)))))
      ;; 画封闭线
      (setq out nil)
      (foreach p pairs
        (setq ln (vla-addline (dt:ms)
                              (vlax-3d-point (car p)) (vlax-3d-point (cadr p))))
        (vla-put-layer ln layer)
        (setq out (cons ln out)))
      out)))

;; v9.36: 把一组实体按同几何在目标图层"再描一层" —— 通用二破口封闭线的
;; "JRTFBX" 定位副本(本体仍在 "JRT"; 供另一项目建模脚本按层定位用)。只取
;; 曲线两端点重建直线(通用二产物恒为直线); 端点按项目惯例 error-p + 非 nil
;; 双判(vlax-curve 越界返 nil 不抛错)。失败跳过不中断。返回新建实体表。
(defun dt:jrt2-trace (objs layer / out o p1 p2 ln ms)
  (setq out nil
        ms  (dt:ms))
  (foreach o objs
    (setq p1 (vl-catch-all-apply 'vlax-curve-getstartpoint (list o))
          p2 (vl-catch-all-apply 'vlax-curve-getendpoint (list o)))
    (if (and (not (vl-catch-all-error-p p1)) (not (vl-catch-all-error-p p2)) p1 p2)
      (progn
        (setq ln (vl-catch-all-apply 'vla-addline
                   (list ms (vlax-3d-point p1) (vlax-3d-point p2))))
        (if (and (not (vl-catch-all-error-p ln)) ln)
          (progn
            (vla-put-layer ln layer)
            (setq out (cons ln out)))))))
  (reverse out))

;; 两点式主流程(process 环节覆盖, c:JRT 内直接调用):
;;   1) JRT 层源线检查 + JRTDW 定位层检查(缺则中止)
;;   2) 按句柄记忆删除上一轮产物(只删仍在 JRT 层的; 源线永不删)
;;   3) 源线过滤(可偏移类型, 跳过零长线头)并按端点相接组成"条"
;;   4) 每条第 k 层(k=1..内向偏移次数)每段朝内侧偏 k×步长
;;      (v9.25: 锚段两候选各整环传播, 取离 FLB 壁更远的环=朝内;
;;       FLB 不可测→围合区域奇偶→JRTDW 就近逐级回退, 与 JRTDW 画向无关)
;;   5) 每条收集全部自由端头(带层号)→ 每个头一条线连最外↔最内
;;   6) 记忆本轮产物句柄 + 统计输出
;; ---------------------------------------------------------------------------
;; 单线自动补边(v9.16, 按用户截图定稿): 用户只画 ①外壁整圈(JRT 层, 闭合轮廓;
;; 请用直线/圆弧/开放多段线, 勿用闭合多段线) ②JRTDW 定位短线(每处出线口一条,
;; 贴着外壁指向板边)。脚本自动完成旧手工三步:
;;   偏移 = JRTDW 朝两边偏 jrt2_half_w → 出线通道两壁线(JRT 层, 持久源线;
;;          v9.26 双端再各延 jrt2_hook_ext(默认5) —— 圆弧/圆外壁在偏移处
;;          "让开", 不延伸则通道线够不着外壁致开口被跳过; 0=旧行为);
;;   裁剪 = 外壁在通道处开口(切口到过渡弧切点为止, 中间段删除);
;;   圆角 = 外壁断头↔通道线过渡弧 jrt2_end_r(任意夹角按 r/tan(α/2) 解析,
;;          直角即 R12, 与手画 FILLET 一致)。
;; 生成件(通道线/过渡弧/切口后壁段)为持久源线, 不入重跑清理表 —— 与手画
;; 产物同权, 之后走原嵌套引擎(嵌套/破口封闭/出线口颈线不变)。
;; 重跑幂等: 该定位短线处已有通道壁线(平行/垂直距≈halfw/有重叠)即跳过。
;; ---------------------------------------------------------------------------

;; 直线单侧偏移(返回偏移实体并放 layer; 失败 nil)
(defun dt:jrt2-offset-line (ln dist layer / r v)
  (setq r (vl-catch-all-apply 'vla-offset (list ln dist)))
  (if (vl-catch-all-error-p r)
    nil
    (progn
      (setq v (car (vlax-safearray->list (vlax-variant-value r))))
      (vla-put-layer v layer)
      v)))

;; 直线双端各延长 ext(v9.26, 出线口通道延伸用): 仅 AcDbLine 生效,
;; 重建新线置 layer 后删原线返回新 vla; ln=nil/ext<=0/非直线/零长 → 原样返回
(defun dt:jrt2-line-extend (ln ext layer / sp ep d dl nx new)
  (if (or (null ln) (null ext) (<= ext 0.0)
          (/= (vla-get-objectname ln) "AcDbLine"))
    ln
    (progn
      (setq sp (vlax-curve-getstartpoint ln)
            ep (vlax-curve-getendpoint ln)
            d  (list (- (nth 0 ep) (nth 0 sp)) (- (nth 1 ep) (nth 1 sp)) 0.0)
            dl (sqrt (+ (* (nth 0 d) (nth 0 d)) (* (nth 1 d) (nth 1 d)))))
      (if (< dl 1e-8)
        ln
        (progn
          (setq nx  (list (/ (nth 0 d) dl) (/ (nth 1 d) dl) 0.0)
                new (vla-addline (dt:ms)
                       (vlax-3d-point
                         (list (- (nth 0 sp) (* (nth 0 nx) ext))
                               (- (nth 1 sp) (* (nth 1 nx) ext)) 0.0))
                       (vlax-3d-point
                         (list (+ (nth 0 ep) (* (nth 0 nx) ext))
                               (+ (nth 1 ep) (* (nth 1 nx) ext)) 0.0))))
          (vla-put-layer new layer)
          (vla-delete ln)
          new)))))

;; 重跑幂等检查: 该定位短线处是否已有通道壁线 —— 源线中存在与 stub 平行
;; (|叉积|<1e-4)、垂直距 ≈ halfw(±0.5)的直线即视为已开过
(defun dt:jrt2-ch-exist (stub srcs halfw / sa ea d ul found s e v vl dd n)
  (setq sa (vlax-curve-getstartpoint stub)
        ea (vlax-curve-getendpoint stub)
        sa (list (nth 0 sa) (nth 1 sa) 0.0)
        ea (list (nth 0 ea) (nth 1 ea) 0.0)
        d  (list (- (nth 0 ea) (nth 0 sa)) (- (nth 1 ea) (nth 1 sa)) 0.0)
        ul (sqrt (+ (* (nth 0 d) (nth 0 d)) (* (nth 1 d) (nth 1 d))))
        found nil)
  (if (> ul 1e-8)
    (progn
      (setq d (list (/ (nth 0 d) ul) (/ (nth 1 d) ul) 0.0))
      (foreach s srcs
        (if (and (null found)
                 (= (vla-get-objectname s) "AcDbLine"))
          (progn
            (setq e (vlax-curve-getstartpoint s)
                  e (list (nth 0 e) (nth 1 e) 0.0)
                  v (vlax-curve-getendpoint s)
                  v (list (nth 0 v) (nth 1 v) 0.0)
                  v (list (- (nth 0 v) (nth 0 e)) (- (nth 1 v) (nth 1 e)) 0.0)
                  vl (sqrt (+ (* (nth 0 v) (nth 0 v)) (* (nth 1 v) (nth 1 v)))))
            (if (> vl 1e-8)
              (progn
                (setq v  (list (/ (nth 0 v) vl) (/ (nth 1 v) vl) 0.0)
                      dd (- (* (nth 0 d) (nth 1 v)) (* (nth 1 d) (nth 0 v))))
                (if (< (abs dd) 1e-4)
                  (progn
                    (setq n  (list (- (nth 0 e) (nth 0 sa)) (- (nth 1 e) (nth 1 sa)) 0.0)
                          dd (- (* (nth 0 n) (nth 1 d)) (* (nth 1 n) (nth 0 d))))
                    (if (< (abs (- (abs dd) halfw)) 0.5)
                      (setq found T))))))))))
  found)
)

;; 曲线与直线实体的交点列表(取该曲线一侧; 无交点 nil)
;; v9.17: dt:cross-points 每对为 (obj . pts) —— 交点列表用 cdr 取(此前误用
;; cadr 拿到首个交点裸点, foreach 对坐标数字求 distance 抛类型错误); 整体
;; 加 catch, 求交异常按"无交点"降级跳过
(defun dt:jrt2-line-x-curve (curve line / res pts)
  (setq res (vl-catch-all-apply 'dt:cross-points (list (list curve line)))
        pts (if (and res (not (vl-catch-all-error-p res)))
              (cdr (nth 0 res))))
  (if (and pts (not (listp (car pts)))) (setq pts (list pts)))
  (if (and pts (> (length pts) 0)) pts nil))

;; 曲线上 pt 处的单位切向(有限差分, 避开 getparamatpoint 浮点坑; 失败 nil)
(defun dt:jrt2-wall-tan (curve pt / dist p1 p2 v ul)
  (setq dist (vl-catch-all-apply 'vlax-curve-getdistatpoint (list curve pt)))
  (if (or (vl-catch-all-error-p dist) (null dist))
    nil
    (progn
      ;; v9.31: 端点侧取样与起点侧对称判空 —— 交点距壁端 <0.01 时
      ;; (+ dist 0.01) 越界, getpointatdist 返 nil 而不抛错(v9.25 头注),
      ;; (nth 0 p2) 直接入减法会抛参数类型错误(v9.25 双判规范漏此一处)
      (setq p1 (vl-catch-all-apply 'vlax-curve-getpointatdist
                 (list curve (max 0.0 (- dist 0.01))))
            p2 (vl-catch-all-apply 'vlax-curve-getpointatdist
                 (list curve (+ dist 0.01))))
      (if (and p1 p2
               (not (vl-catch-all-error-p p1))
               (not (vl-catch-all-error-p p2)))
        (progn
          (setq v  (list (- (nth 0 p2) (nth 0 p1)) (- (nth 1 p2) (nth 1 p1)) 0.0)
                ul (sqrt (+ (* (nth 0 v) (nth 0 v)) (* (nth 1 v) (nth 1 v)))))
          (if (< ul 1e-9)
            nil
            (list (/ (nth 0 v) ul) (/ (nth 1 v) ul) 0.0)))
        nil))))

;; 交点列表里取离指定点最近者
(defun dt:jrt2-near-pt (pts ref / best bd p dd)
  (setq best nil bd 1e99)
  (foreach p pts
    (setq dd (distance p ref))
    (if (< dd bd) (setq bd dd best p)))
  best)

;; v9.28: 曲线在点 p 处的密切圆 —— 返回 (半径 圆心) 或 nil(直壁/求值失败)。
;; 曲率半径 Rw = |f'|^3 / |f'×f''|, 圆心在曲线转弯一侧(cross>0 取左法向)。
;; getparamatpoint 对浮点偏移点可能返 nil(坑#86 同源), 一律 catch 后判空;
;; 曲率≈0(直壁)→ nil, 调用方走线-线公式。
(defun dt:jrt2-osculating (curve p / par f1 f2 cr ul rw nx ny)
  (setq par (vl-catch-all-apply 'vlax-curve-getparamatpoint (list curve p)))
  (if (and par (not (vl-catch-all-error-p par)) (numberp par))
    (progn
      (setq f1 (vl-catch-all-apply 'vlax-curve-getfirstderiv (list curve par))
            f2 (vl-catch-all-apply 'vlax-curve-getsecondderiv (list curve par)))
      (if (and f1 f2
               (not (vl-catch-all-error-p f1))
               (not (vl-catch-all-error-p f2)))
        (progn
          (setq ul (sqrt (+ (* (nth 0 f1) (nth 0 f1)) (* (nth 1 f1) (nth 1 f1))))
                cr (- (* (nth 0 f1) (nth 1 f2)) (* (nth 1 f1) (nth 0 f2))))
          (if (and (> ul 1e-12) (> (abs cr) 1e-9))
            (progn
              (setq rw (/ (* ul ul ul) (abs cr))
                    nx (if (> cr 0.0) (- (/ (nth 1 f1) ul)) (/ (nth 1 f1) ul))
                    ny (if (> cr 0.0) (/ (nth 0 f1) ul) (- (/ (nth 0 f1) ul))))
              (list rw (list (+ (nth 0 p) (* rw nx))
                             (+ (nth 1 p) (* rw ny)) 0.0)))))))))

;; v9.28: 外壁密切圆(osc=(Rw Cw))与通道线的解析真切圆角。
;; 圆角心 c = p + t·d + r·m (m = d 的法向且 dot(m,w)>0, 保证心在保留壁侧),
;; 解 |c-Cw| = Rw+r (外切, 凸壁 S 弯肩部) / Rw-r (内切, 凹壁) 的一元二次,
;; 取满足 t>0(切点在靠板边侧) 且 切壁点 tp=Cw+Rw·unit(c-Cw) 落在保留壁侧
;; (dot(tp-p,w)>0) 的根。返回 (tp fp c) 或 nil(无有效解, 调用方回退线-线)。
(defun dt:jrt2-true-fillet (p w d r osc / rw cw m qx qy bx cx rr disc rt t1 t2
                               tt c ux uy dl tp fp res)
  (if osc
    (progn
      (setq rw (car osc)
            cw (cadr osc)
            m  (list (- (nth 1 d)) (nth 0 d) 0.0))
      (if (< (+ (* (nth 0 m) (nth 0 w)) (* (nth 1 m) (nth 1 w))) 0.0)
        (setq m (list (- (nth 0 m)) (- (nth 1 m)) 0.0)))
      (setq qx (+ (- (nth 0 p) (nth 0 cw)) (* r (nth 0 m)))
            qy (+ (- (nth 1 p) (nth 1 cw)) (* r (nth 1 m)))
            bx (* 2.0 (+ (* (nth 0 d) qx) (* (nth 1 d) qy))))
      ;; 依次试外切/内切半径, 各取两根, 首个通过校验者胜
      (foreach rr (append (list (+ rw r))
                          (if (> (- rw r) 1e-9) (list (- rw r)) nil))
        (if (null res)
          (progn
            (setq cx   (- (+ (* qx qx) (* qy qy)) (* rr rr))
                  disc (- (* bx bx) (* 4.0 cx)))
            (if (>= disc 0.0)
              (progn
                (setq rt (sqrt disc)
                      t1 (/ (- (- 0.0 bx) rt) 2.0)
                      t2 (/ (- rt bx) 2.0))
                (foreach tt (list t1 t2)
                  (if (and (null res) (> tt 1e-9))
                    (progn
                      (setq c  (list (+ (nth 0 p) (* tt (nth 0 d)) (* r (nth 0 m)))
                                     (+ (nth 1 p) (* tt (nth 1 d)) (* r (nth 1 m)))
                                     0.0)
                            ux (- (nth 0 c) (nth 0 cw))
                            uy (- (nth 1 c) (nth 1 cw))
                            dl (sqrt (+ (* ux ux) (* uy uy))))
                      (if (> dl 1e-9)
                        (progn
                          (setq tp (list (+ (nth 0 cw) (* rw (/ ux dl)))
                                         (+ (nth 1 cw) (* rw (/ uy dl)))
                                         0.0)
                                fp (list (+ (nth 0 p) (* tt (nth 0 d)))
                                         (+ (nth 1 p) (* tt (nth 1 d)))
                                         0.0))
                          (if (> (+ (* (- (nth 0 tp) (nth 0 p)) (nth 0 w))
                                    (* (- (nth 1 tp) (nth 1 p)) (nth 1 w)))
                                 1e-9)
                            (setq res (list tp fp c)))))))))))))
      res)))

;; 过渡弧(外壁曲线与通道线在角点 p 的圆角, 解析法): w = 沿外壁远离开口的
;; 单位向量, d = 沿通道线指向板边的单位向量。v9.28: 壁为曲线时按其角点
;; 密切圆解析求真切(切点落在壁上而非切线上, 三段端点严格重合且 G1);
;; 直壁(曲率≈0)或求解失败回退线-线公式: 切点距 t = r/tan(α/2)(直角即 r),
;; 切点 T = p + t·w(壁上) / F = p + t·d(通道线上), 弧心 = T + n·r
;; (n = w 的垂直方向上指向 d 一侧)。返回 (弧 T F) 或 nil(两线近平行)。
(defun dt:jrt2-hook-arc (p w d r layer wall / ms dot n nl osc best t-len tp fp c
                            a1 a2 sw tmp arc)
  (setq dot (+ (* (nth 0 d) (nth 0 w)) (* (nth 1 d) (nth 1 w))))
  (if (> (abs dot) 0.9999)
    (progn (princ "\n【通用二】出线口: 定位线与外壁近平行, 该处跳过。") nil)
    (progn
      (setq n  (list (- (nth 1 w)) (nth 0 w) 0.0)
            nl (sqrt (+ (* (nth 0 n) (nth 0 n)) (* (nth 1 n) (nth 1 n))))
            n  (list (/ (nth 0 n) nl) (/ (nth 1 n) nl) 0.0))
      (if (< (+ (* (nth 0 d) (nth 0 n)) (* (nth 1 d) (nth 1 n))) 0.0)
        (setq n (list (- (nth 0 n)) (- (nth 1 n)) 0.0)))
      ;; v9.28: 曲线壁按密切圆求真切圆角; 直壁/失败回退线-线公式
      (setq osc  (if wall (dt:jrt2-osculating wall p))
            best (if osc (dt:jrt2-true-fillet p w d r osc)))
      (if best
        (setq tp (car best) fp (cadr best) c (caddr best))
        (progn
          (if osc
            (princ "\n【通用二】出线口: 过渡弧真切求解失败, 该切点按切线近似处理。"))
          (setq t-len (/ (* r (+ 1.0 dot))
                         (sqrt (- 1.0 (* dot dot))))
                tp (list (+ (nth 0 p) (* t-len (nth 0 w)))
                         (+ (nth 1 p) (* t-len (nth 1 w))) 0.0)
                fp (list (+ (nth 0 p) (* t-len (nth 0 d)))
                         (+ (nth 1 p) (* t-len (nth 1 d))) 0.0)
                c  (list (+ (nth 0 tp) (* r (nth 0 n)))
                         (+ (nth 1 tp) (* r (nth 1 n))) 0.0))))
      (setq a1 (angle '(0.0 0.0 0.0) (mapcar '- tp c))
            a2 (angle '(0.0 0.0 0.0) (mapcar '- fp c))
            sw (- a2 a1))
      (if (< sw 0.0) (setq sw (+ sw (* 2.0 pi))))
      (if (> sw pi) (setq tmp a1 a1 a2 a2 tmp))
      (setq ms  (vla-get-modelspace (vla-get-activedocument (vlax-get-acad-object)))
            arc (vla-addarc ms (vlax-3d-point c) r a1 a2))
      (vla-put-layer arc layer)
      (list arc tp fp))))

;; 把通道线裁到过渡弧切点: 保留 keepfrom → 靠 out-pt(板边端)一侧的端点,
;; 删原线返回新线(放 JRT 层)。v9.27: 比较方向修正 —— 旧代码"保留离
;; out-pt 远的端点", 只在 pw 求交失效(恒得起笔端)时碰巧结果正确, 属双重
;; 负负得正; pw 修正后必须改为"保留离 out-pt 近的端点"才是注释本意。
;; (v9.27 起本函数仅为区域分类弃权时的兜底路径)
(defun dt:jrt2-trim-line (line keepfrom out-pt / s e newobj)
  (setq s (vlax-curve-getstartpoint line)
        e (vlax-curve-getendpoint line)
        s (list (nth 0 s) (nth 1 s) 0.0)
        e (list (nth 0 e) (nth 1 e) 0.0)
        keepfrom (list (nth 0 keepfrom) (nth 1 keepfrom) 0.0)
        out-pt (list (nth 0 out-pt) (nth 1 out-pt) 0.0))
  (if (< (distance s out-pt) (distance e out-pt))
    (setq e s))
  (vla-delete line)
  (setq newobj (vla-addline (dt:ms) (vlax-3d-point keepfrom) (vlax-3d-point e)))
  (vla-put-layer newobj "JRT")
  newobj)

;; v9.27: 直线端点里外分类 —— 返回"落在轮廓围合区域外"的那一端点;
;; 两端同里/同外/区域不可判 → nil(调用方走旧启发式兜底)
;; (v9.32: 本函数从未被调用 —— v9.27 实际落地为 hook-one 内联分类,
;;  全库零引用, 死代码删除; 历史定义见 git)

;; 用 [p1 p2] 重建直线段(置 JRT 层), 删原线返回新 vla(v9.27 裁剪用)
(defun dt:jrt2-seg-rebuild (ln p1 p2 / new)
  (setq new (vla-addline (dt:ms) (vlax-3d-point p1) (vlax-3d-point p2)))
  (vla-put-layer new "JRT")
  (vla-delete ln)
  new)

;; 单条定位短线 → 在其外壁上开 S 形出线口。返回更新后的 srcs(失败原样)。
;; 流程: 通道线 = stub 朝两边偏 halfw → 双端各延 ext(v9.26, 圆弧/圆外壁在
;;       偏移处"让开", 短线够不着; ext=jrt2_hook_ext 默认5, 0=旧行为) →
;;       定位线两端按轮廓围合区域分里外(v9.27) → 找两线都穿过的外壁 →
;;       角点/切向(d=里→外) → 过渡弧×2 → 外壁在两切点间开口(保留段重建,
;;       原线删) → 通道线保留[过渡弧切点→定位线外端垂足](v9.29: 延长仅
;;       求交用, 外端裁回定位线端, 不高于 JRTDW)。
(defun dt:jrt2-hook-one (stub srcs halfw r ext / typ sa ea d ul ch1 ch2 wall
                            pu pl pw e-out p-out region s-in s-out oe1 oe2
                            w1 w2 r1 r2 arc1 arc2 tu tl fp1 fp2 cutp pa pb pe
                            p1 p2 nch1 nch2 o s out)
  (setq typ (vla-get-objectname stub))
  (cond
    ((/= typ "AcDbLine")
     (princ "\n【通用二】出线口: JRTDW 定位线含非直线实体, 该处跳过。")
     srcs)
    ((dt:jrt2-ch-exist stub srcs halfw)
     srcs)
    (T
     (setq sa (vlax-curve-getstartpoint stub)
           ea (vlax-curve-getendpoint stub)
           sa (list (nth 0 sa) (nth 1 sa) 0.0)
           ea (list (nth 0 ea) (nth 1 ea) 0.0)
           d  (list (- (nth 0 ea) (nth 0 sa)) (- (nth 1 ea) (nth 1 sa)) 0.0)
           ul (sqrt (+ (* (nth 0 d) (nth 0 d)) (* (nth 1 d) (nth 1 d)))))
     (cond
       ((< ul 1e-8)
        (princ "\n【通用二】出线口: JRTDW 定位线零长, 跳过。")
        srcs)
        (T
          (setq d   (list (/ (nth 0 d) ul) (/ (nth 1 d) ul) 0.0)
                ch1 (dt:jrt2-line-extend
                      (dt:jrt2-offset-line stub halfw "JRT") ext "JRT")
                ch2 (dt:jrt2-line-extend
                      (dt:jrt2-offset-line stub (- 0.0 halfw) "JRT") ext "JRT"))
         ;; v9.27: 定位线两端按轮廓围合区域分里外 —— 一头埋板内的长定位线
         ;; 不再依赖"离交点远=板边"假设; 两端同里/同外 → 保持 nil 走旧启发式
         (setq region (dt:jrt2-region-edges-n srcs 12) s-in nil s-out nil)
         (cond
           ((and (dt:jrt2-pt-inside sa region) (not (dt:jrt2-pt-inside ea region)))
            (setq s-in sa s-out ea))
           ((and (dt:jrt2-pt-inside ea region) (not (dt:jrt2-pt-inside sa region)))
            (setq s-in ea s-out sa)))
        (cond
          ((or (null ch1) (null ch2))
           (foreach o (append (if ch1 (list ch1) nil) (if ch2 (list ch2) nil))
             (vla-delete o))
           (princ "\n【通用二】出线口: 通道线偏移失败, 该处跳过。")
           srcs)
          (T
           (setq wall nil pu nil pl nil)
           (foreach s srcs
             (if (null wall)
               (progn
                 (setq pu (dt:jrt2-near-pt (dt:jrt2-line-x-curve s ch1) sa)
                       pl (dt:jrt2-near-pt (dt:jrt2-line-x-curve s ch2) sa))
                 (if (and pu pl) (setq wall s) (setq pu nil pl nil)))))
           (cond
              ((null wall)
               (foreach o (list ch1 ch2) (vla-delete o))
               (princ "\n【通用二】出线口: 通道线未与外壁相交(定位线未贴外壁/该处已开口/延伸不足, 可加大 出线口通道延伸), 跳过。")
               srcs)
             (T
              (setq w1 (dt:jrt2-wall-tan wall pu)
                    w2 (dt:jrt2-wall-tan wall pl))
              (cond
                ((or (null w1) (null w2))
                 (foreach o (list ch1 ch2) (vla-delete o))
                 (princ "\n【通用二】出线口: 外壁切向求解失败, 该处跳过。")
                 srcs)
                (T
                 ;; 切向取"背离另一条通道线"的方向
                 (if (< (+ (* (nth 0 (mapcar '- pu pl)) (nth 0 w1))
                           (* (nth 1 (mapcar '- pu pl)) (nth 1 w1))) 0.0)
                   (setq w1 (list (- (nth 0 w1)) (- (nth 1 w1)) 0.0)))
                 (if (< (+ (* (nth 0 (mapcar '- pl pu)) (nth 0 w2))
                           (* (nth 1 (mapcar '- pl pu)) (nth 1 w2))) 0.0)
                   (setq w2 (list (- (nth 0 w2)) (- (nth 1 w2)) 0.0)))
                  ;; d 取指向板边方向: v9.27 优先"里端→外端"(轮廓区域分类);
                  ;; 分类不可用 → 回退 v9.22 "定位线上远离外壁角点的一端"
                  (if s-out
                    (setq d (dt:unit (list (- (nth 0 s-out) (nth 0 s-in))
                                           (- (nth 1 s-out) (nth 1 s-in)) 0.0)))
                    (if (< (distance ea pu) (distance sa pu))
                      (setq d (list (- (nth 0 d)) (- (nth 1 d)) 0.0))))
                 (setq r1 (dt:jrt2-hook-arc pu w1 d r "JRT" wall)
                       r2 (dt:jrt2-hook-arc pl w2 d r "JRT" wall))
                 (cond
                   ((or (null r1) (null r2))
                    (foreach o (append (if r1 (list (car r1)) nil)
                                       (if r2 (list (car r2)) nil)
                                       (list ch1 ch2))
                      (vla-delete o))
                    (princ "\n【通用二】出线口: 过渡弧生成失败, 半成品已清理, 该处跳过。")
                    srcs)
                   (T
                    (setq arc1 (car r1) tu (cadr r1) fp1 (caddr r1)
                          arc2 (car r2) tl (cadr r2) fp2 (caddr r2)
                          cutp (dt:cut-params wall (list tu tl))
                          pa   (nth 1 cutp)
                          pb   (nth 2 cutp)
                          pe   (last cutp))
                    (if (or (null pa) (null pb) (< (- pb pa) 1e-6))
                      (progn
                        (foreach o (list arc1 arc2 ch1 ch2) (vla-delete o))
                        (princ "\n【通用二】出线口: 开口区间异常, 该处跳过。")
                        srcs)
                       (progn
                         (if (> pa 1e-6)
                           (setq p1 (dt:rebuild-seg wall 0.0 pa "JRT")))
                         (if (> (- pe pb) 1e-6)
                           (setq p2 (dt:rebuild-seg wall pb pe "JRT")))
                         ;; v9.27: pw/e-out 必须在删 wall 之前算(v9.22 版放在
                         ;; 删后, 对已删实体求交恒失败 → e-out 退化成起笔端,
                         ;; 保留侧随画向翻转); 兜底路径自此真正可用
                         (setq pw (dt:jrt2-near-pt
                                    (dt:jrt2-line-x-curve stub wall) sa)
                               e-out (if (and pw (< (distance sa pw) (distance ea pw)))
                                       ea
                                       sa)
                               ;; v9.29: 外端复原 = 通道线裁回定位线原始外端
                               ;; (hook_ext 延长仅求交用, 用完即裁回);
                               ;; 垂足投影, 与区域分类解耦
                               p-out (if s-out s-out e-out)
                               oe1 (vlax-curve-getClosestPointTo ch1 p-out)
                               oe2 (vlax-curve-getClosestPointTo ch2 p-out))
                         (vla-delete wall)
                         ;; v9.29: 通道线保留 [过渡弧切点 → 定位线外端] ——
                         ;; 板内伸出段删除, 外端不留延长(高于定位线即错)
                         (setq nch1 (if oe1 (dt:jrt2-seg-rebuild ch1 fp1 oe1)
                                      (dt:jrt2-trim-line ch1 fp1 e-out))
                               nch2 (if oe2 (dt:jrt2-seg-rebuild ch2 fp2 oe2)
                                      (dt:jrt2-trim-line ch2 fp2 e-out)))
                        (setq out (vl-remove wall srcs))
                        (if p1 (setq out (cons p1 out)))
                        (if p2 (setq out (cons p2 out)))
                        (setq out (append out (list arc1 arc2 nch1 nch2)))
                        (princ (strcat "\n【通用二】出线口已开: 通道偏移 ±"
                                       (rtos halfw 2 1) " + 过渡弧 R"
                                       (rtos r 2 1) "。"))
                        out)))))))))))))))

;; 出线口总控(v9.16): 对每条 JRTDW 直线定位短线, 在其外壁上开 S 形出线口。
;; 返回更新后的 srcs(生成件/切口段均为持久源线)。
(defun dt:jrt2-hooks (srcs dw-vlas / stub)
  (foreach stub dw-vlas
    (setq srcs (dt:jrt2-hook-one stub srcs *jrt2-half-w* *jrt2-end-r*
                                 *jrt2-hook-ext*)))
  srcs)

(defun dt:jrt2-process ( / doc layers srcs bars dw-all dw-vlas bar-made made ents
                           kmap neck-ents obj obj-type len ends clns clns-tr h
                           nbar nlayers nclose k kmax d bar flb-v)
  ;; ---- 1) 源线与 JRTDW 定位层检查 ----
  (setq srcs (if (tblsearch "LAYER" "JRT") (dt:layer-vlas "JRT")))
  (if (null srcs)
    (princ "\n【提示】图层 \"JRT\" 上没有任何源线, 请先在 JRT 图层绘制加热条源线。")
    (progn
      ;; v9.25: FLB 曲线集(嵌套内偏方向的判据, 一次收集全流程复用)
      (setq flb-v (if (tblsearch "LAYER" "FLB") (dt:curves-only (dt:layer-vlas "FLB"))))
      (setq dw-all (if (tblsearch "LAYER" "JRTDW") (dt:layer-vlas "JRTDW"))
            dw-vlas nil)
      (foreach obj dw-all
        (if (member (vla-get-objectname obj)
                    '("AcDbLine" "AcDbLWPolyline" "AcDbPolyline"
                      "AcDbArc" "AcDbCircle" "AcDbEllipse" "AcDbSpline"))
          (setq dw-vlas (cons obj dw-vlas))))
      (if (null dw-vlas)
        (princ "\n【提示】图层 \"JRTDW\" 上没有可用的曲线实体 —— 两点式以 JRTDW(加热条定位)为向内基准, 请在该层画定位线(直线/弧等)再运行。")
        (progn
          (setq doc    (vla-get-activedocument (vlax-get-acad-object))
                layers (vla-get-layers doc))
          (dt:ensure-layer layers "JRT" 2 "黄色")
          (dt:ensure-layer layers "JRTFBX" 21 "浅橙")
          ;; ---- 2) 删除上一轮产物(句柄记忆; v9.31: "JT" 层出线口产物一并
          ;;         清除 —— 旧版只认 "JRT", 颈线/两壁/封口/圆角重跑永不
          ;;         清除逐次叠加; v9.34 起 "JRTFBX" 层一并清除(v9.36
          ;;         该层为定位副本);
          ;;         仅清 *jrt2-made* 记忆句柄, flb 假体的
          ;;         JT 实体不在记忆中, 不受影响) ----
          (dt:jrt-undo-mark)
          (foreach h *jrt2-made*
            (if (handent h)
              (progn
                (setq obj (vlax-ename->vla-object (handent h)))
                (if (member (vl-catch-all-apply 'vla-get-layer (list obj))
                            '("JRT" "JT" "JRTFBX"))
                  (vl-catch-all-apply 'vla-delete (list obj))))))
          (dt:jrt-undo-end)
          ;; ---- 3) 源线过滤并组成"条" ----
          (setq srcs nil)
          (foreach obj (dt:layer-vlas "JRT")
            (setq obj-type (vla-get-objectname obj))
            (if (member obj-type
                        '("AcDbLine" "AcDbLWPolyline" "AcDbPolyline"
                          "AcDbArc" "AcDbCircle" "AcDbEllipse" "AcDbSpline"))
              (progn
                (setq len (vlax-curve-getdistatparam
                            obj (vlax-curve-getendparam obj)))
                (if (> len 0.001)
                  (setq srcs (cons obj srcs))))
              (princ (strcat "\n【警告】JRT 层存在不可偏移类型("
                             obj-type "), 已跳过。"))))
          ;; v9.16 单线补边: 每条 JRTDW 定位短线处自动开 S 形出线口
          ;; (偏移通道线 + 外壁开口 + 过渡圆角; 生成件为持久源线, 重跑幂等)
          (setq srcs (dt:jrt2-hooks srcs dw-vlas))
          (setq bars (dt:jrt2-group srcs 0.5))
          (princ (strcat "\n【通用二】JRT 源线 " (itoa (length srcs))
                         " 段, 并为 " (itoa (length bars)) " 条。"))
          ;; ---- 4)+5) 逐条: 逐层内偏 + 破口封闭 ----
          (setq made nil kmap nil nbar 0 nlayers 0 nclose 0)
          (foreach bar bars
            (setq nbar (1+ nbar))
            (dt:jrt-undo-mark)
            (setq bar-made nil
                  k 1
                  kmax (max 0 (fix *jrt-inner-count*)))
            (while (<= k kmax)
              (setq d (* k *jrt-inner-step*))
              (if (> d 0.0)
                (progn
                   (setq ents (dt:jrt2-layer bar d "JRT" dw-vlas flb-v))
                  (if ents
                    (progn
                      (setq bar-made (append bar-made ents)
                            kmap (append (mapcar '(lambda (o) (cons o k)) ents)
                                         kmap))))
                  (setq nlayers (1+ nlayers))
                  (princ (strcat "\n【通用二】条 " (itoa nbar) " 第 " (itoa k)
                                 " 层(偏移 " (rtos d 2 2) "): 成功 "
                                 (itoa (length ents)) " / "
                                 (itoa (length bar)) " 段。")))
                (princ "\n【警告】向内偏移步长<=0, 忽略本层。"))
              (setq k (1+ k)))
            ;; 源线 = 最外侧(k=0); 每个头一条封闭线连最外↔最内
            ;; v9.36: 封闭线本体放 "JRT"(加热条结构保持完整), 另在 "JRTFBX"
            ;;   描同几何定位副本(dt:jrt2-trace) —— 供建模脚本按层定位
            (setq kmap (append (mapcar '(lambda (o) (cons o 0)) bar) kmap)
                  ends (dt:jrt2-free-ends (append bar bar-made) 0.5)
                  clns (dt:jrt2-close ends kmap "JRT")
                  clns-tr (dt:jrt2-trace clns "JRTFBX")
                  bar-made (append bar-made clns clns-tr)
                  made (append made bar-made)
                  nclose (+ nclose (length clns)))
            (princ (strcat "\n【通用二】条 " (itoa nbar) ": 破口封闭 "
                           (itoa (length clns)) " 条(两头各连最外↔最内 → \"JRT\"), "
                           "另描定位副本 → \"JRTFBX\"。"))
            (dt:jrt-undo-end))
          ;; ---- 5.5) 出线口: JRTDW×FLB 颈线(通用二) ----
          (setq neck-ents (dt:jrt2-neck dw-vlas))
          (if neck-ents
            (progn
              (setq made (append made neck-ents))
              (princ (strcat "\n【通用二】出线口已生成 "
                             (itoa (length neck-ents)) " 个对象(\"JT\"图层)。"))))
          ;; ---- 6) 记忆本轮产物句柄 + 统计 ----
          (setq *jrt2-made*
                 (mapcar '(lambda (o) (vla-get-handle o)) made))
          (princ (strcat "\n【完成】通用二加热条已生成 → \"JRT\"图层(黄色), "
                         "封闭线定位副本 → \"JRTFBX\"(浅橙): "
                         (itoa nbar) " 条, 共 " (itoa nlayers) " 层 / "
                         (itoa (length made)) " 个对象, 破口封闭 "
                         (itoa nclose) " 条; 源线未改动。模板: "
                         (nth 0 (dt:jrt-template-row)) "。"))
          ))))
  (princ))

;; 两直线在公共端点处的圆角(解析法, v9.10 出线口用):
;; 圆心取两保留段方向(角点→各自另一端)的角平分线上, 切点回修两线,
;; 加劣弧; 半径放不下时按 1 递减(最低 1)。仅支持直线(弧段返回 nil)。
;; 返回圆弧 vla 对象(失败 nil)
(defun dt:jrt2-fillet2 (ln1 ln2 r layer / p1a p1b p2a p2b pc o1 o2 u1 u2
                            cosv ang2 ok r0 tt t1 t2 bis c a1 a2 dd arc pa pb)
  (setq p1a (vlax-curve-getstartpoint ln1)
        p1b (vlax-curve-getendpoint ln1)
        p2a (vlax-curve-getstartpoint ln2)
        p2b (vlax-curve-getendpoint ln2)
        pc nil)
  ;; 找公共端点(角点)
  (foreach pa (list p1a p1b)
    (foreach pb (list p2a p2b)
      (if (and (not pc) (< (distance pa pb) 0.01))
        (setq pc pa))))
  (if pc
    (progn
      (setq o1 (if (< (distance p1a pc) 0.01) p1b p1a)
            o2 (if (< (distance p2a pc) 0.01) p2b p2a)
            u1 (dt:unit (mapcar '- o1 pc))
            u2 (dt:unit (mapcar '- o2 pc))
            cosv (+ (* (car u1) (car u2)) (* (cadr u1) (cadr u2))))
      (if (< (abs cosv) 0.999)
        (progn
          (setq ang2 (/ (dt:acos cosv) 2.0)
                r0 r
                ok nil)
          ;; 半径递减: 切点不得超出线段
          (while (and (not ok) (>= r0 1.0))
            (setq tt (/ r0 (dt:tan ang2)))
            (if (and (<= tt (distance pc o1)) (<= tt (distance pc o2)))
              (setq ok T)
              (setq r0 (1- r0))))
          (if ok
            (progn
              (setq t1 (dt:pt+vec pc u1 tt)
                    t2 (dt:pt+vec pc u2 tt)
                    bis (dt:unit (mapcar '+ u1 u2))
                    c (dt:pt+vec pc bis (/ r0 (sin ang2)))
                    a1 (angle (list (car c) (cadr c)) (list (car t1) (cadr t1)))
                    a2 (angle (list (car c) (cadr c)) (list (car t2) (cadr t2)))
                    dd (- a2 a1))
              (if (< dd 0.0) (setq dd (+ dd (* 2.0 pi))))
              ;; 劣弧: 逆时针跨度超过半圆则反向画
              (if (> dd pi)
                (setq arc (vla-addarc (dt:ms) (vlax-3d-point c) r0 a2 a1))
                (setq arc (vla-addarc (dt:ms) (vlax-3d-point c) r0 a1 a2)))
              (vla-put-layer arc layer)
              ;; 两线端头回修到切点(弧向随保留段, 与 JRT 出线处一致)
              (dt:set-endpoint ln1 (if (< (distance p1a pc) 0.01) "S" "E") t1)
              (dt:set-endpoint ln2 (if (< (distance p2a pc) 0.01) "S" "E") t2)
              arc)))))))

;; 相交处圆角(v9.11 修正弧向): 颈壁与原 JT 线相交于 pt-x。切点:
;; 壁上 t1 = pt-x 沿 dirv(朝 cap/走廊内)走 tt; 原JT线保留段上
;; t2 = pt-x 沿其保留方向(远离走廊)走 tt; 圆心 = t1 + 法向*r。
;; 弧倒掉 pt-x 处尖角, 与 JRT 出线处圆弧同向。
;; wall/piece 均需为 LINE; 返回圆弧 vla(失败 nil)
(defun dt:jrt2-junction (wall pt-x pint dirv piece r layer /
                         w-s w-e w-cap p-s p-e p-o u1 u2 dotv ang2 ok r0 tt
                         t1 t2 n1 n c a1 a2 dd arc)
  (setq w-s (vlax-curve-getstartpoint wall)
        w-e (vlax-curve-getendpoint wall)
        w-cap (if (< (distance pint w-s) (distance pint w-e)) w-e w-s)
        u1  (dt:unit dirv)                        ; 壁上朝 cap/走廊内方向
        p-s (vlax-curve-getstartpoint piece)
        p-e (vlax-curve-getendpoint piece)
        p-o (if (> (distance pint p-s) (distance pint p-e)) p-s p-e)
        u2  (dt:unit (mapcar '- p-o pt-x))
        dotv (+ (* (car u1) (car u2)) (* (cadr u1) (cadr u2))))
  (cond
    ((>= (abs dotv) 0.999)
     (princ (strcat "\n【警告】出线口: 相交处两线近共线(dot=" (rtos dotv 2 3) "), 暂不圆角。"))
     nil)
    (T
     (setq ang2 (/ (dt:acos dotv) 2.0)
           ok nil
           r0 r)
     (while (and (not ok) (>= r0 1.0))
       (setq tt (/ r0 (dt:tan ang2)))
       (if (and (<= tt (distance pt-x w-cap))
                (<= tt (distance pt-x p-o)))
         (setq ok T)
         (setq r0 (1- r0))))
     (if (null ok)
       (progn
         (princ (strcat "\n【警告】出线口: 圆角R放不下(壁可用"
                        (rtos (distance pt-x w-cap) 2 1)
                        ", JT段可用" (rtos (distance pt-x p-o) 2 1) "), 暂不圆角。"))
         nil)
       (progn
         (setq t1 (dt:pt+vec pt-x u1 tt)
               t2 (dt:pt+vec pt-x u2 tt)
               n1 (list (- (cadr u1)) (car u1) 0.0)
               n  (if (> (+ (* (car n1) (car u2)) (* (cadr n1) (cadr u2))) 0.0)
                    n1
                    (list (- (car n1)) (- (cadr n1)) 0.0))
               c  (dt:pt+vec t1 n r0)
               a1 (angle (list (car c) (cadr c)) (list (car t1) (cadr t1)))
               a2 (angle (list (car c) (cadr c)) (list (car t2) (cadr t2)))
               dd (- a2 a1))
         (if (< dd 0.0) (setq dd (+ dd (* 2.0 pi))))
         ;; 劣弧: 逆时针跨度超过半圆则反向画
         (if (> dd pi)
           (setq arc (vla-addarc (dt:ms) (vlax-3d-point c) r0 a2 a1))
           (setq arc (vla-addarc (dt:ms) (vlax-3d-point c) r0 a1 a2)))
         (vla-put-layer arc layer)
         ;; 两线回修到切点(壁修靠 pint 侧端, JT线修 pt-x 侧端)
         (dt:set-endpoint wall (if (< (distance pint w-s) (distance pint w-e)) "S" "E") t1)
         (dt:set-endpoint piece
           (if (< (distance pt-x p-s) (distance pt-x p-e)) "S" "E") t2)
         arc)))))

;; 出线口(v9.10, 通用二): JRTDW 定位线与 FLB 相交, 从交点画颈线(JT 层,
;; 长 jrt2-neck-len), ±jrt2-neck-off 偏移成两壁; 远端画封闭线封口,
;; 两角 R=jrt2-close-r 圆角; 两壁与原 JT 线相交处:
;; 裁掉走廊带内(距 JRTDW 轴线<neck-off)的原 JT 线段与壁伸入 JT 区域的
;; 多余段, 相交处 R=jrt2-trim-r 圆角(弧向随保留段, 与 JRT 出线处一致)。
;; v9.24: 颈线方向 = FLB 外侧, FLBJT 恒朝外、不入侵 FLB, 与 JRTDW 画向无关。
;; v9.26: 方向主判据升级为 FLB 围合区域奇偶点内(对 L 形/带台阶非凸外框
;;        同样正确, 修复"某些情况仍入侵 FLB"); 判据不可得时才回退 v9.24
;;        包围盒中心规则。FLB 曲线按 24 段/曲线采样(R≤400 弦割误差<探针5)。
;; 返回本功能新建对象 vla 列表
(defun dt:jrt2-neck (dw-vlas / out flb flb-edges flb-bb flb-cen jt-snap dwc p-s p-e pint pt f2
                          cp xpts far dirv r clen walls w ws we wf wends cl arc
                          e2 cutc wall-x pt-x fresh out-e pc partner rr p sgn wx)
  (setq out nil)
  (setq flb (if (tblsearch "LAYER" "FLB") (dt:layer-vlas "FLB")))
  (if (null flb)
    (princ "\n【提示】图层 \"FLB\" 不存在, 跳过出线口绘制。")
    (progn
      ;; v9.26: 主判据 FLB 围合区域边集(24 段采样); 兜底包围盒中心
      (setq flb-edges (dt:jrt2-region-edges-n (dt:curves-only flb) 24))
      (setq flb-bb (dt:rect-bbox (dt:curves-only flb))
            flb-cen (if flb-bb
                      (list (/ (+ (car flb-bb) (caddr flb-bb)) 2.0)
                            (/ (+ (cadr flb-bb) (cadddr flb-bb)) 2.0) 0.0)
                      nil))
      (setq jt-snap (dt:jrt-snapshot "JT"))   ; 原 JT 线快照(只裁这些)
      (dt:jrt-undo-mark)
      (foreach dwc dw-vlas
        (setq p-s (vlax-curve-getstartpoint dwc)
              p-e (vlax-curve-getendpoint dwc)
              pint nil)
        ;; 相交点 = JRTDW 端头落在 FLB 上(容差 0.5)
        (foreach pt (list p-s p-e)
          (if (null pint)
            (foreach f2 flb
              (if (null pint)
                (progn
                  (setq cp (vl-catch-all-apply 'vlax-curve-getclosestpointto
                             (list f2 pt)))
                  (if (and (not (vl-catch-all-error-p cp))
                           (< (distance pt cp) 0.5))
                    (setq pint pt)))))))
        ;; 兜底: 与 FLB 实际求交
        (if (null pint)
          (foreach f2 flb
            (if (null pint)
              (progn
                (setq xpts (dt:inters-pts dwc f2))
                (if xpts (setq pint (car xpts)))))))
        (if pint
          (progn
            (setq far (if (< (distance pint p-s) (distance pint p-e))
                        p-e p-s)
                  dirv (dt:unit (mapcar '- far pint))
                  ;; v9.26: 颈线方向恒朝 FLB 外侧 —— 主判据: 交点沿 dirv 走
                  ;;        5mm 若落在 FLB 围合区域内(奇偶判定, 非凸也对)
                  ;;        → 反向; 围合边集不可得时回退 v9.24 包围盒中心
                  ;;        距离判据; 两者都不可用 → 保持原向(v9.10 旧行为)
                  dirv (if (if flb-edges
                             (dt:jrt2-pt-inside (dt:pt+vec pint dirv 5.0) flb-edges)
                             (and flb-cen
                                  (< (distance (dt:pt+vec pint dirv 5.0) flb-cen)
                                     (distance pint flb-cen))))
                         (list (- (car dirv)) (- (cadr dirv)) 0.0)
                         dirv))
            ;; 1) 颈线(构图线, JT 层): 偏移出两壁后即删除不保留
            (setq clen (vla-addline (dt:ms)
                         (vlax-3d-point pint)
                         (vlax-3d-point (dt:pt+vec pint dirv *jrt2-neck-len*))))
            (vla-put-layer clen "JT")
            ;; 2) 两壁(±jrt2-neck-off)
            (setq walls nil)
            (foreach sgn (list *jrt2-neck-off* (- *jrt2-neck-off*))
              (setq r (vl-catch-all-apply 'vla-offset (list clen sgn)))
              (if (not (vl-catch-all-error-p r))
                (progn
                  (setq w (car (vlax-safearray->list (vlax-variant-value r))))
                  (vla-put-layer w "JT")
                  (setq out (cons w out)
                        walls (cons w walls)))))
            (vl-catch-all-apply 'vla-delete (list clen))
            (if (< (length walls) 2)
              (princ "\n【警告】出线口: 颈线偏移失败, 跳过该出线口。")
              (progn
                ;; 3) 远端封闭线(两壁离交点较远的端头相连)
                (setq wends nil)
                (foreach w walls
                  (setq ws (vlax-curve-getstartpoint w)
                        we (vlax-curve-getendpoint w)
                        wf (if (< (distance pint ws) (distance pint we))
                             we ws))
                  (setq wends (cons wf wends)))
                (setq cl (vla-addline (dt:ms)
                           (vlax-3d-point (car wends))
                           (vlax-3d-point (cadr wends))))
                (vla-put-layer cl "JT")
                (setq out (cons cl out))
                ;; 4) 封口两角 R=jrt2-close-r
                (foreach w walls
                  (setq arc (dt:jrt2-fillet2 w cl *jrt2-close-r* "JT"))
                  (if arc (setq out (cons arc out))))
                ;; 5) 各壁与原 JT 线的第一交点(裁剪前计算)
                ;;    注意: dt:jrt-snapshot 返回的是图元名 ename 而非句柄
                (setq wall-x nil)
                (foreach w walls
                  (setq xpts nil)
                  (foreach e2 jt-snap
                    (setq cutc (vlax-ename->vla-object e2))
                    (setq xpts (append xpts (dt:inters-pts w cutc))))
                  (if xpts
                    (progn
                      (setq pt-x (car xpts))
                      (foreach p xpts
                        (if (< (distance p pint) (distance pt-x pint))
                          (setq pt-x p)))
                      (setq wall-x (cons (list w pt-x) wall-x)))))
                ;; 6) 裁掉走廊带内(距 JRTDW 轴线<neck-off)的原 JT 线段
                ;;    逐条保护: 一条裁剪失败只跳过该条并打印原因
                (foreach e2 jt-snap
                  (setq cutc (vlax-ename->vla-object e2))
                  (setq xpts (append (dt:inters-pts cutc (nth 0 walls))
                                     (dt:inters-pts cutc (nth 1 walls))))
                  (if xpts
                    (progn
                      (setq rr (vl-catch-all-apply 'dt:jrt-cut-curve
                                 (list cutc xpts "JT" dw-vlas *jrt2-neck-off* "TRIM")))
                      (if (vl-catch-all-error-p rr)
                        (princ (strcat "\n【警告】出线口: 一条 JT 线裁剪失败已跳过: "
                                       (vl-catch-all-error-message rr)))))))
                ;; 7) 相交处 R=jrt2-trim-r 圆角(壁裁 pint 侧至切点, 弧向随
                ;;    保留段, 与 JRT 出线处一致)
                (setq out-e (mapcar 'vlax-vla-object->ename out))
                (foreach wx wall-x
                  (setq w (car wx)
                        pt-x (cadr wx)
                        fresh (dt:jrt-snapshot "JT")
                        partner nil)
                  (foreach e2 fresh
                    (if (and (not partner)
                             (not (member e2 out-e)))
                      (progn
                        (setq pc (vlax-ename->vla-object e2))
                        (if (and (= (vla-get-objectname pc) "AcDbLine")
                                 (or (< (distance (vlax-curve-getstartpoint pc) pt-x) 0.01)
                                     (< (distance (vlax-curve-getendpoint pc) pt-x) 0.01)))
                          (setq partner pc)))))
                  (if partner
                    (progn
                      (setq rr (vl-catch-all-apply 'dt:jrt2-junction
                                 (list w pt-x pint dirv partner *jrt2-trim-r* "JT")))
                      (if (vl-catch-all-error-p rr)
                        (princ "\n【警告】出线口: 相交处圆角失败, 暂不圆角。")
                        (progn
                          (setq arc rr
                                out (cons arc out)
                                out-e (cons (vlax-vla-object->ename arc) out-e)))))
                    (princ "\n【警告】出线口: 相交处为弧段或未找到相接段, 暂不圆角。"))))))))
      (if (null out)
        (princ "\n【提示】JRTDW 与 FLB 无相交点, FLBJT 未生成 —— 请把 JRTDW 延长至与 FLB 相交后重跑(颈线只在与 FLB 相交处开出)。"))
      (dt:jrt-undo-end)
      out)))

;; ============================================================================
;; 六、参数对话框(结构与主脚本一致, 回调/文件名改名隔离)
;; ============================================================================

;; 参数键 → 中文标签(参数框 edit_box 标签; 动态生成与命令行汇总共用)
(setq dt:jrt-param-labels
      '(("jrt_offset"      . "流道线偏移距离:")
        ("jrt_cap_inset"   . "封闭线内偏移距离:")
        ("jrt_fillet_r"    . "圆角半径R:")
        ("jrt_cap_r"       . "封闭线圆角半径R:")
        ("jrt_inner_step"  . "向内偏移步长:")
        ("jrt_inner_count" . "内向偏移次数:")
        ("jrt2_neck_len"   . "出线颈线长度:")
        ("jrt2_neck_off"   . "出线颈线偏移:")
        ("jrt2_close_r"    . "出线封口圆角R:")
        ("jrt2_trim_r"     . "出线相交圆角R:")
        ("jrt2_half_w"     . "出线口通道半宽:")
        ("jrt2_end_r"      . "出线口过渡圆角R:")
        ("jrt2_hook_ext"   . "出线口通道延伸:")))

;; 当前模板用到的参数键列表(= 模板参数默认表的键序; v9.9 起参数框动态化)
(defun dt:jrt-tpl-keys ( / )
  (mapcar 'car (nth 2 (dt:jrt-template-row))))

;; 内置 DCL 源文本(外部 jrt_runner.dcl 不存在时自动生成, 总是覆盖保证同步)
;; 参数框 edit_box 按当前模板的参数键动态生成(两个一行; 通用一 6 项/通用二 8 项)
(defun dt:jrt-dcl-lines ( / keys lines row k1 k2)
  (setq keys (mapcar 'car dt:jrt-param-table) lines nil)
  (while keys
    (setq k1 (car keys)
          k2 (cadr keys)
          row (list "    : row {"
                    (strcat "      : edit_box { key = \"" k1
                            "\"; label = \"" (cdr (assoc k1 dt:jrt-param-labels))
                            "\"; edit_width = 10; }")))
    (if k2
      (setq row (append row
        (list (strcat "      : edit_box { key = \"" k2
                      "\"; label = \"" (cdr (assoc k2 dt:jrt-param-labels))
                      "\"; edit_width = 10; }")))
            keys (cddr keys))
      (setq keys nil))
    (setq lines (append lines row (list "    }"))))
  (append
    (list
      "jrt_param : dialog {"
      "  label = \"加热条参数设置\";"
      "  : boxed_radio_column {"
      "    label = \"模板\";"
      "    : radio_button { key = \"tpl0\"; label = \"通用一 (LD源线偏移, 无出线口)\"; }"
      "    : radio_button { key = \"tpl1\"; label = \"通用二 (JRT外壁整圈+JRTDW出线口)\"; }"
      "  }"
      "  : boxed_column {"
      "    label = \"加热条参数\";")
    lines
    (list
      "  }"
      "  : row {"
      "    : button { key = \"reset\"; label = \"恢复默认\"; width = 10; }"
      "    spacer;"
      "    ok_button;"
      "    cancel_button;"
      "  }"
      "}")))
(defun dt:jrt-write-dcl (path / f ln)
  (setq f (open path "w"))
  (if f
    (progn
      ;; v9.14: 写中途异常也保证 close(半截 dcl 由对话框链的 catch 提示)
      (vl-catch-all-apply
        '(lambda ( )
           (foreach ln (dt:jrt-dcl-lines)
             (write-line ln f)))
        nil)
      (close f)
      path)
    nil))

;; 查找对话框文件路径: **确定性目录**——优先 dt_start 引导器注入的
;; *dt-script-dir*(vl-propagate 全文档可见), 无 dt_start 时写系统 TEMP。
;; v9.11b 重写: 删除旧 findfile 候选链(v95~v98 文件名均已不存在)——多副本
;; 环境下 findfile 会命中支持路径里其它目录的同名旧副本, 与 offset/slot 统一。
;; 总是用内置源覆盖生成最新 dcl(界面参数永远与脚本同步)。
(defun dt:jrt-find-dcl ( / )
  (if (and *dt-script-dir* (/= *dt-script-dir* ""))
    (dt:jrt-write-dcl (strcat *dt-script-dir* "\\jrt_runner.dcl"))
    (dt:jrt-write-dcl (strcat (getenv "TEMP") "\\jrt_runner_tmp.dcl"))))

;; 读取编辑框数值: 空/非法输入时返回默认值 def
;; v9.13: atof 对垃圾串静默返回 0(如 "abc" -> 0.0), 参数会被悄悄改成 0;
;;        改用 distof —— 非法输入返回 nil 可识别, 回退默认值(坑 #54)
(defun dt:jrt-get-num (key def / s v)
  (setq s (get_tile key)
        v (if (and s (/= s "")) (distof s) nil))
  (if v v def))

;; 恢复默认参数到对话框(恢复默认按钮回调; 只刷当前模板的键 —— 控件按
;; 模板动态生成, 键不存在 set_tile 会报错);
;; v9.12 = 恢复 ini 配置默认值(先重读配置, 改 ini 后点恢复默认立即生效)
(defun dt:jrt-param-reset ( / val p)
  (setq *jrt-cfg* (dt:jrt-cfg-read (strcat (dt:jrt-cfg-dir) "\\jrt_runner.ini")))
  (foreach p dt:jrt-param-table
    (if (member (car p) (dt:jrt-tpl-keys))
      (progn
        (setq val (dt:jrt-param-default (car p)))
        (set_tile (car p) (rtos val 2 2))))))

;; 应用对话框值到全局参数(确定按钮回调; 空/非法输入回退当前值;
;; 只读当前模板的键, 其余参数保持不变);
;; v9.12: 应用后自动保存记忆(取消不触发本回调, 天然"确定才记忆")
(defun dt:jrt-param-apply ( / p v)
  (setq *jrt-template* *jrt-tpl-pick*)   ; v9.37: 面板单选即当前模板
  (foreach p dt:jrt-param-table
    (if (member (car p) (dt:jrt-tpl-keys))
      (progn
        (setq v (dt:jrt-get-num (car p) (eval (cadr p))))
        ;; v9.14: 负值校验 —— 距离/半径类参数 <0 回退当前值(负值会画出退化几何)
        (if (< v 0.0) (setq v (eval (cadr p))))
        (set (cadr p) v))))
  (dt:jrt-mem-save))

;; 弹出参数对话框
;; 返回: T=用户点"确定"(参数已应用到全局变量), nil=取消/加载失败
(defun dt:jrt-param-dialog ( / dcl-file dcl-id result p)
  (setq *jrt-cfg* (dt:jrt-cfg-read (strcat (dt:jrt-cfg-dir) "\\jrt_runner.ini")))
  (setq *jrt-tpl-pick* *jrt-template*)
  (setq dcl-file (dt:jrt-find-dcl))
  (if (null dcl-file)
    (progn
      (princ "\n【界面】无法生成对话框文件(磁盘权限不足?), 界面不可用。")
      nil)
    (progn
      ;; v9.14: load_dialog 对损坏 dcl 是抛错而非返回 nil, 包 catch;
      ;;   start_dialog 同理 —— 保证 unload_dialog 必被执行
      (setq dcl-id (vl-catch-all-apply 'load_dialog (list dcl-file)))
      (if (or (vl-catch-all-error-p dcl-id) (null dcl-id))
        (progn
          (princ "\n【界面】对话框加载失败。")
          nil)
        (progn
          (if (new_dialog "jrt_param" dcl-id)
            (progn
              (set_tile (strcat "tpl" (itoa *jrt-tpl-pick*)) "1")
              (action_tile "tpl0" "(dt:jrt-tpl-switch 0)")
              (action_tile "tpl1" "(dt:jrt-tpl-switch 1)")
              (foreach p dt:jrt-param-table
                (set_tile (car p)
                  (rtos (if (member (car p) (dt:jrt-tpl-keys))
                          (eval (cadr p))
                          (dt:jrt-param-default (car p)))
                        2 2)))
              (dt:jrt-tpl-mode *jrt-tpl-pick*)
              (action_tile "reset" "(dt:jrt-param-reset)")
              (action_tile "accept" "(dt:jrt-param-apply)(done_dialog 1)")
              (action_tile "cancel" "(done_dialog 0)")
              (setq result (vl-catch-all-apply 'start_dialog nil))
              (unload_dialog dcl-id)
              (if (and (not (vl-catch-all-error-p result)) (= result 1)) T nil))
            (progn
              (unload_dialog dcl-id)
              (princ "\n【界面】对话框初始化失败。")
              nil)))))))

;; v9.37: 面板内切换模板 —— 单选更新 + 非当前模板的独有参数置灰
(defun dt:jrt-tpl-mode (i / k)
  (foreach k (list "jrt_offset" "jrt_cap_inset" "jrt_fillet_r" "jrt_cap_r")
    (mode_tile k (if (= i 0) 0 1)))
  (foreach k (list "jrt2_neck_len" "jrt2_neck_off" "jrt2_close_r" "jrt2_trim_r"
                   "jrt2_half_w" "jrt2_end_r" "jrt2_hook_ext")
    (mode_tile k (if (= i 1) 0 1)))
  (princ))

(defun dt:jrt-tpl-switch (i)
  (setq *jrt-tpl-pick* i)
  (set_tile "tpl0" (if (= i 0) "1" "0"))
  (set_tile "tpl1" (if (= i 1) "1" "0"))
  (dt:jrt-tpl-mode i)
  (princ))

(defun dt:jrt-apply-template (idx quiet / tpl params p v)
  (setq *jrt-template* idx
        tpl (nth idx dt:jrt-template-table)
        params (nth 2 tpl))
  (foreach p dt:jrt-param-table
    (setq v (cond ((cdr (assoc (car p) (dt:jrt-cfg-sec *jrt-mem* (car tpl)))))
                  ((dt:jrt-cfg-get *jrt-cfg* (car tpl) (car p)))
                  ((cdr (assoc (car p) params)))
                  (T (caddr p))))
    (set (cadr p) v))
  (if (null quiet)
    (princ (strcat "\n【模板】已选择 \"" (nth 0 tpl) "\": " (nth 1 tpl) "。")))
  (princ))

;; 独立模板选择框(v9.8): 单选模板 → 确定=采用该模板, 取消=nil(中止流程)
;; v9.12: 打开前重读 ini 配置(改配置后切模板立即用新默认)
(defun c:JRTPARAM ( / p txt)
  (if (dt:jrt-param-dialog)
    (progn
      (setq txt (strcat "\n参数已保存(模板: " (nth 0 (dt:jrt-template-row)) "):"))
      (foreach p (dt:jrt-tpl-keys)
        (setq txt (strcat txt " " (cdr (assoc p dt:jrt-param-labels)) " "
                          (rtos (eval (cadr (assoc p dt:jrt-param-table))) 2 2))))
      (princ (strcat txt "。")))
    (princ "\n已取消, 参数未修改。"))
  (princ))

;; ============================================================================
;; 七、主命令 c:JRT —— 在命令行输入 JRT 即可执行
;; ============================================================================
(defun c:JRT ( / *error* doc layers ld rz plans matched total k kmax hw inset r capr proc)

  ;; ---- 内部错误处理: 出错或按 ESC 中断时给出友好提示 ----
  ;; v9.14: 兜底闭合可能悬挂的 UNDO 组(无开放组时无副作用, catch 双保险)
  (defun *error* (msg)
    ;; v9.17 坑 #69: *error* 内禁止 (command) —— 改用 COM 撤销标记收尾
    (dt:jrt-undo-end)
    (princ (strcat "\n程序已停止: " (if msg msg "用户按 ESC 取消")))
    (princ)
  )

  ;; v9.20: 移除 v9.18 的入口守卫 —— defun 只设函数槽不设值槽,
  ;; (null 函数名) 恒为 T, 该守卫对完整加载也恒误报(坑 #72), 已删。
  (if (null (dt:jrt-param-dialog))
    (princ "\n已取消, 未执行加热条绘制。")
    (if (setq proc (cdr (assoc 'process (nth 3 (dt:jrt-template-row)))))
        ;; 模板自管主流程(当前为 "通用二", v9.9 引入): 源图层检查/清理旧产物/偏移/
        ;; 封口/统计全部在覆盖函数内完成, 不走下方内置 LD 流程
        (apply proc nil)
        (progn
      ;; 第 1 步: 检查源图层
      (if (null (tblsearch "LAYER" "LD"))
        (princ "\n【提示】图层 \"LD\" 不存在, 请先绘制流道中心线(LD 图层)或运行 OFF 后重试。")
        (progn
          (setq ld (dt:curves-only (dt:layer-vlas "LD")))
          (if (null ld)
            (princ "\n【提示】图层 \"LD\" 上没有任何对象, 无法绘制加热条。")
            (progn
              ;; 第 2 步: 建层 + 清理上一轮产物
              (setq doc    (vla-get-activedocument (vlax-get-acad-object))
                    layers (vla-get-layers doc))
              (dt:ensure-layer layers "JRT" 2 "黄色")
              (dt:jrt-undo-mark)
              (setq total (dt:purge-layer "JRT"))
              (dt:jrt-undo-end)
              (princ (strcat "\n已清理上一轮产物 " (itoa total)
                             " 个对象(\"JRT\"图层)。"))
              ;; 第 3 步: RZ 热咀圆检查(圆帽依赖; 缺失则全部直线帽)
              (setq rz (dt:layer-vlas "RZ"))
              (if (null rz)
                (princ "\n【警告】未找到 \"RZ\" 图层(请先运行 OFF), 全部端头将使用直线帽。")
                (princ (strcat "\n找到 \"RZ\" 热咀圆 " (itoa (length rz)) " 个。")))
              ;; 第 4 步: 端头收集 + RZ 匹配 + 帽形式判定(decide 环节,
              ;;          各层共用; 模板可覆盖判定规则)
              (setq matched (dt:jrt-match-rz (dt:jrt-free-ends ld) rz))
              (setq plans (dt:jrt-stage 'decide 'dt:jrt-decide (list ld matched)))
              ;; 第 5 步: 多层完整轮廓(外层 + 内向偏移 inner-count 次, 每次收 inner-step)
              (setq kmax 0)
              (if (> *jrt-inner-step* 0.0)
                (setq kmax (min (max 0 (fix *jrt-inner-count*))
                                (fix (/ (- *jrt-offset* 1.0) *jrt-inner-step*))))
                (if (> (fix *jrt-inner-count*) 0)
                  (princ "\n【警告】向内偏移步长<=0, 忽略内向偏移次数。")))
              (setq k 0)
              (while (<= k kmax)
                (setq hw    (- *jrt-offset* (* k *jrt-inner-step*))
                      inset (+ *jrt-cap-inset* (* k *jrt-inner-step*))
                      ;; 内层圆角逐层 +步长: 与外层交汇肩部圆弧同心嵌套(19→23→27)
                      r     (max 1.0 (+ *jrt-fillet-r* (* k *jrt-inner-step*)))
                      capr  (+ *jrt-cap-r* (* k *jrt-inner-step*)))
                (dt:jrt-stage 'build 'dt:jrt-build (list hw inset r capr plans))
                (setq k (1+ k)))
              (if (< kmax (max 0 (fix *jrt-inner-count*)))
                (princ "\n【提示】部分内层因半宽过小未生成。"))
              ;; 第 6 步: 统计输出
              (princ (strcat "\n【完成】加热条半成品已生成 → \"JRT\"图层(黄色)。"
                             "共 " (itoa (1+ kmax)) " 层完整轮廓, LD 源线未改动。"
                             "模板: " (nth 0 (dt:jrt-template-row)) "。"))
            )
          )
        )
      )
    )
    )
  )
  (princ)  ; 静默退出, 不打印返回结果
)
;;; 加载时在命令行输出提示
(dt:jrt-cfg-boot)
;; v9.20: 移除 v9.19 的加载自检 —— atoms-family 在部分环境不返回函数符号
;; (实证: 文件尾已成功调用的 dt:jrt-cfg-boot 也被报"缺失"), 检测不可靠(坑 #72);
;; 半加载若真发生, 运行时的 no function definition 报错本身即准确诊断。
(princ (strcat "\n加热条工具已加载 " *dt-jrt-ver* ": JRT=执行 / JRTPARAM=参数。"))
(princ)
